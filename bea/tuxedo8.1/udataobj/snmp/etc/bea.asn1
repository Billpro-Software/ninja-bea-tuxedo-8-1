-- bea.asn1 - ASN.1 file for BEA's private MIB
-- Last updated 7/26/2001

BEA-MIB { iso org(3) dod(6) internet(1) private(4)
    enterprises(1) bea(140) }

DEFINITIONS ::= BEGIN

IMPORTS
     enterprises, Counter
     FROM RFC1155-SMI
     OBJECT-TYPE
     FROM RFC-1212
     DisplayString
     FROM RFC1213-MIB
     TRAP-TYPE
     FROM RFC-1215;

bea               OBJECT IDENTIFIER ::= { enterprises 140 }
-- bea		  OBJECT IDENTIFIER ::= { iso org(3) dod(6) internet(1) private(4) enterprises(1) 140 }

-- *****************************************************************
-- the main bea groups
-- Please contact BEA Systems, Inc. if you wish to
-- create MIB groups under the "bea" oid in order to avoid
-- possible conflicts.
-- *****************************************************************

beaSystem	     OBJECT IDENTIFIER ::= { bea 1 }	-- BEA system
beaIntAgt	     OBJECT IDENTIFIER ::= { bea 200 }  -- Inteligent Agent

-- *****************************************************************
-- beaSystem group
-- *****************************************************************
-- This group is kept for compatibility purpose, and will be used
-- to pass traps generated by Integrator polling rules
-- *****************************************************************

beaSysDescr OBJECT-TYPE
     SYNTAX  DisplayString
     ACCESS  read-only
     STATUS  mandatory
     DESCRIPTION
               "Kept for compatiblility purpose, and is use
                to pass traps generated by Integrator polling rules"
     ::= { beaSystem 1 }

-- Using beaIntAgtTable MIB, New rules may be created and
-- old ones can be deleted/modified. For more information, about the
-- intelligent agent MIB of BEA Manager SNMP Integrator, please
-- refer to BEA Manager SNMP Integrator, Installation & User's Guide.

beaIntAgtTable OBJECT-TYPE
     SYNTAX  SEQUENCE OF BeaIntAgtEntry
     ACCESS  not-accessible
     STATUS  mandatory
     DESCRIPTION 
               "Intelligent Agent MIB table."
     ::= { beaIntAgt 1 }

beaIntAgtEntry OBJECT-TYPE
     SYNTAX  BeaIntAgtEntry
     ACCESS  not-accessible
     STATUS  mandatory
     DESCRIPTION 
               "Row of attributes in the Int Agent MIB table."
     INDEX { beaIntAgtRuleId }
     ::= { beaIntAgtTable 1 }

BeaIntAgtEntry ::= SEQUENCE {
     beaIntAgtRuleId
       DisplayString,
     beaIntAgtScanIntvl
        INTEGER,
     beaIntAgtRuleAction
        DisplayString,
     beaIntAgtStatus
        INTEGER
     }   

beaIntAgtRuleId   OBJECT-TYPE
     SYNTAX  DisplayString
     ACCESS  read-write
     STATUS  mandatory
     DESCRIPTION 
               "Index into the Int Agent MIB table."
     ::=  { beaIntAgtEntry 1 }

beaIntAgtScanIntvl   OBJECT-TYPE
     SYNTAX  INTEGER
     ACCESS  read-write
     STATUS  mandatory
     DESCRIPTION 
               "interval in seconds for evaluating the rules"
     ::=  { beaIntAgtEntry 2 }

beaIntAgtRuleAction       OBJECT-TYPE
     SYNTAX  DisplayString
     ACCESS  read-write
     STATUS  mandatory
     DESCRIPTION 
               "Rule and action: e.g., if (VAL(.1.3.6.1.4.1.140.1.0) >= 20) 
		{ TRAP_ERR=200 TRAP_OK=300 } : This rule-action specifies 
		that if the value of the OID .1.3.6.1.4.1.140.1.0 is greater
		than 20, send a trap with specific trap id 200. When the 
		situation becomes normal ( i.e., this values becomes less
		than 20), send an SNMP trap with specific trap id 300"
     ::=  { beaIntAgtEntry 3 }
 
beaIntAgtStatus     OBJECT-TYPE
     SYNTAX  INTEGER {
                active(1),
                invalid(2),
                inactive(3)
     }          
     ACCESS  read-write
     STATUS  mandatory
     DESCRIPTION 
               "Status of the rule. 
	GET requests:

	active(1)
		represents that the rule is valid and is being processed by the 
		Integrator.  

	inactive(3) 
		represents that the rule is valid but rule is not being processed 
		by the Integrator.  
	invalid(2)
		represents that the rule is no more valid.

	SET requests:
	active(1)
		Activate this rule if it is in inactive(2) state.

	inactive(3)
		Inactivate this rule if it is in the active(1) state.

	invalid(2)
		remove this rule permanently."
     ::=  { beaIntAgtEntry 4 }

-- *************************************************************************
-- Sample Trap Definition for user defined Traps generated by Agent 
-- Integrator through sample RULE_ACTION entry in beamgr.conf
-- You can add similar definitions for any rules you define/uncoment in 
-- beamgr.conf, in a private copy of bea.asn1 and re-import/load the MIB in 
-- you management platform.
-- *************************************************************************

tranStateErrTrap TRAP-TYPE
        ENTERPRISE beaSysDescr
        VARIABLES {
                beaTrapDescr
        }
        DESCRIPTION
      " Format of beaTrapDescr
        'Rule id %RULE_ID has triggered from OK to ERR state'

        This trap is generated when the sample integrator rule 'tranState' (see beamgr.conf) 
	triggers from an OK to ERR state. "
        ::= 306

tranStateOkTrap TRAP-TYPE
        ENTERPRISE beaSysDescr
        VARIABLES {
                beaTrapDescr
        }
        DESCRIPTION
      " Format of beaTrapDescr
        'Rule id %RULE_ID has triggered from ERR to OK state'

        This trap is generated when the sample integrator rule 'tranState' (see beamgr.conf)
        triggers from an ERR to OK state. "
        ::= 307

-- *********************** Beginning of TUXEDO MIB **********************
-- BEA-TUX-MIB { iso org(3) dod(6) internet(1) private(4) enterprises(1) 
-- 			bea(140) }
--
-- DEFINITIONS ::= BEGIN

-- IMPORTS
--      mgmt, NetworkAddress, IpAddress, Counter, Gauge, TimeTicks, enterprises
--      FROM RFC1155-SMI
--      OBJECT-TYPE
--      FROM RFC-1212
--      TRAP-TYPE
--      FROM RFC-1215;
--	bea          	OBJECT IDENTIFIER ::= { enterprises 140 }


-- PLEASE NOTE: 
-- 1.		Some objects in this MIB can be set (updated) only under 
--		certain states of the TUXEDO system. If you get an ERROR
--		while trying to set read-write object in this MIB please
--		refer to the ULOG file.  For details refer to TM_MIB(5)
--		in the Tuxedo System Reference manual. 

-- 2.		If an object does not exist, the agent may return '-1' for
--		numeric and '-' for DisplayString type objects respectively,
--		instead of returning 'noSuchName'.

tuxedo          OBJECT IDENTIFIER ::= { bea 300 }

tuxWsmib	OBJECT IDENTIFIER ::= { tuxedo 1 }
tuxEvents	OBJECT IDENTIFIER ::= { tuxedo 2 }
tuxTdomain	OBJECT IDENTIFIER ::= { tuxedo 3 }
tuxTgroup	OBJECT IDENTIFIER ::= { tuxedo 4 }
tuxTmachine	OBJECT IDENTIFIER ::= { tuxedo 5 }
tuxTmsg		OBJECT IDENTIFIER ::= { tuxedo 6 }
tuxTqueue	OBJECT IDENTIFIER ::= { tuxedo 7 }
tuxTrouting	OBJECT IDENTIFIER ::= { tuxedo 8 }
tuxTulog	OBJECT IDENTIFIER ::= { tuxedo 9 }
tuxTsvc   	OBJECT IDENTIFIER ::= { tuxedo 10 }
tuxTAcl		OBJECT IDENTIFIER ::= { tuxedo 11 }
tuxTAppQ	OBJECT IDENTIFIER ::= { tuxedo 12 }
tuxTBridge	OBJECT IDENTIFIER ::= { tuxedo 16 }
tuxTclient	OBJECT IDENTIFIER ::= { tuxedo 17 }
tuxTconn	OBJECT IDENTIFIER ::= { tuxedo 18 }
tuxTdevice	OBJECT IDENTIFIER ::= { tuxedo 19 }
tuxTserver	OBJECT IDENTIFIER ::= { tuxedo 20 }
tuxTlisten	OBJECT IDENTIFIER ::= { tuxedo 21 }
tuxTransaction	OBJECT IDENTIFIER ::= { tuxedo 23 }
tuxTnetGroup	OBJECT IDENTIFIER ::= { tuxedo 28 }
tuxTnetMap	OBJECT IDENTIFIER ::= { tuxedo 33 }
tuxTserverCtxt	OBJECT IDENTIFIER ::= { tuxedo 34 }


--*****************************************************************
-- tuxWsmib Group
-- This group defines a set of objects which enable the management of 
-- /WS  group (one WSL and its associated WSH processes).
-- *****************************************************************


-- *****************************************************************
-- The tuxTwshTbl table represents runtime attributes of workstation
-- handler  client processes. These objects characterize /WS statistics 
-- specific to a  particular WSH client process when it is active . 
-- All objects in this group are available only when the corresponding
-- WSH is active.
-- *****************************************************************

tuxTwshTbl OBJECT-TYPE
	SYNTAX 	SEQUENCE OF TuxTwshEntry
	ACCESS	not-accessible
	STATUS	mandatory
	DESCRIPTION
		" A table which represents runtime attributes of WSH
		 client processes."	
	::= { tuxWsmib 1 }

tuxTwshEntry OBJECT-TYPE
	SYNTAX	TuxTwshEntry
	ACCESS	not-accessible
	STATUS	mandatory
	DESCRIPTION
		" This object depicts one row (corresponding to one 
		 workstation handler) in the tuxTwshTbl table.

		 NOTE: All objects in this MIB group are local attributes i.e.
		       values for these objects correspond to the local host
		       only, where the TUXEDO agent is running. So the user needs
		       to run an instance of the TUXEDO agent on every node for
		       which these values are of interest."
	INDEX 	{ tuxTwshTaPid }
	::= { tuxTwshTbl 1 }

TuxTwshEntry ::= SEQUENCE {
	tuxTwshTaClientId
		DisplayString,
	tuxTwshTaWshClientId
		DisplayString,
	tuxTwshTaSrvGrp
		DisplayString,
	tuxTwshTaSrvId
		INTEGER,
	tuxTwshTaGrpNo
		INTEGER,
	tuxTwshTaState
		INTEGER,
	tuxTwshTaLmid
		DisplayString,
	tuxTwshTaPid
		INTEGER,
	tuxTwshTaNaddr
		DisplayString,
	tuxTwshTaHwClients
		INTEGER,
	tuxTwshTaMultiplex
		INTEGER,
	tuxTwshTaCurClients
		INTEGER,
	tuxTwshTaTimeleft
		INTEGER,
	tuxTwshTaActive
		INTEGER,
	tuxTwshTaTotacttime
		INTEGER,
	tuxTwshTaTotidltime
		INTEGER,
	tuxTwshTaCurwork
		INTEGER,
	tuxTwshTaFlowcnt
		INTEGER,
	tuxTwshTaNumblockQ
		INTEGER,
	tuxTwshTaRcvdByt
		INTEGER,
	tuxTwshTaRcvdNum
		INTEGER,
	tuxTwshTaSentByt
		INTEGER,
	tuxTwshTaSentNum
		INTEGER
	}


tuxTwshTaClientId OBJECT-TYPE	
        SYNTAX  DisplayString ( SIZE (1..78) )
        ACCESS  read-only
        STATUS  mandatory
        DESCRIPTION
                " Client identifier for this WSH.  The data in this field
                 should  not  be  interpreted  directly  by the end user
        	 except for equality comparison."
        ::= { tuxTwshEntry 1 }

			
tuxTwshTaWshClientId OBJECT-TYPE	
        SYNTAX  DisplayString ( SIZE (1..78) )
        ACCESS  read-only
        STATUS  mandatory
        DESCRIPTION
                " Client identifier for this WSH.  The data in this field
                 should  not  be  interpreted  directly  by the end user
        	 except for equality comparison. Value is same as  
		 TaClientID"
        ::= { tuxTwshEntry 2 }

tuxTwshTaSrvGrp OBJECT-TYPE	
        SYNTAX  DisplayString ( SIZE (1..30) )
        ACCESS  read-only
        STATUS  mandatory
        DESCRIPTION
                " Logical name of the server  group  for  the  associated
          	 WSL. "
        ::= { tuxTwshEntry 3 }

tuxTwshTaSrvId OBJECT-TYPE	
        SYNTAX  INTEGER (1..30001)
        ACCESS  read-only
        STATUS  mandatory
        DESCRIPTION
                " Unique (within the server group) server  identification
        	  number for the associated WSL. "
        ::= { tuxTwshEntry 4 }

tuxTwshTaGrpNo OBJECT-TYPE  
        SYNTAX  INTEGER   (1..30000)
        ACCESS  read-only
        STATUS  mandatory
        DESCRIPTION    
                " "
        ::= { tuxTwshEntry 5 }

tuxTwshTaState OBJECT-TYPE  
        SYNTAX  INTEGER {  
	   active(1),
	   suspended(2),
	   dead(3)
	   }
        ACCESS  read-write
        STATUS  mandatory
        DESCRIPTION    
                " State for the WSH client within the  application. Any state
		 defined  for the tuxTclientTbl group may be returned
		 or set . State  changes to the suspended(2) state are 
		 transitive to all clients associated with this WSH as is  the
		 resetting  of  a suspended(2)  WSH  to active(1).  
		 Additionally, suspended WSH clients will not be  assigned  any
		 additional incoming clients by the WSL.
          	 Note that the state of a WSH client may not be  set  to 
          	 dead(3)  when  accessing  the tuxTclientTbl group; however, the
          	 state transition to dead(3) is allowed via the tuxTwshTbl group
          	 and will result in all connections being handled by the
          	 targetted WSH to be dropped abortively."
        ::= { tuxTwshEntry 6 }

tuxTwshTaLmid OBJECT-TYPE
        SYNTAX  DisplayString ( SIZE (1..30) )
        ACCESS  read-only
        STATUS  mandatory
        DESCRIPTION
                " Current logical machine on which the WSH is running."
        ::= { tuxTwshEntry 7 }

tuxTwshTaPid OBJECT-TYPE
        SYNTAX  INTEGER
        ACCESS  read-only
        STATUS  mandatory
        DESCRIPTION
                " Native operating system process identifier for the  WSH
          	  client. "
        ::= { tuxTwshEntry 8 }

tuxTwshTaNaddr OBJECT-TYPE
        SYNTAX  DisplayString ( SIZE (1..256) )
        ACCESS  read-only
        STATUS  mandatory
        DESCRIPTION   
                " Network address of  workstation  handler.   Hexadecimal
          	  addresses are converted to an ascii format with a lead-
          	  ing 0x. "
        ::= { tuxTwshEntry 9 }

tuxTwshTaHwClients OBJECT-TYPE
        SYNTAX  INTEGER ( 1..32767 )
        ACCESS  read-only
        STATUS  mandatory 
        DESCRIPTION     
                " High water number of clients accessing application  via
          	  this WSH. "
        ::= { tuxTwshEntry 10 } 
 
tuxTwshTaMultiplex OBJECT-TYPE
        SYNTAX  INTEGER ( 1..32767 )
        ACCESS  read-only
        STATUS  mandatory 
        DESCRIPTION      
                " Maximum number of clients that may access the  applica-
          	  tion via this WSH. "
        ::= { tuxTwshEntry 11 }
 
tuxTwshTaCurClients OBJECT-TYPE 
        SYNTAX  INTEGER ( 1..32767 ) 
        ACCESS  read-only
        STATUS  mandatory  
        DESCRIPTION       
                " Current number of  clients  accessing  application  via
          	  this WSH. "
        ::= { tuxTwshEntry 12 } 
  
tuxTwshTaTimeleft OBJECT-TYPE  
        SYNTAX  INTEGER 
        ACCESS  read-only
        STATUS  mandatory   
        DESCRIPTION        
                " A non-0 value for this attribute indicates that the WSH
          	  has been assigned a newly connecting workstation client
          	  that has the indicated amount of time, in  seconds,  
		  to complete the initialization process with the WSH. "
        ::= { tuxTwshEntry 13 }  
   
tuxTwshTaActive OBJECT-TYPE   
        SYNTAX  INTEGER {
		yes(1),
		no(2),
		unknown(3) 
		}
        ACCESS  read-only
        STATUS  mandatory    
        DESCRIPTION        
                " A value of yes(1) indicates that the WSH is  currently  per-
          	  forming  work on behalf of one of its associated works-
          	  tation clients.  A value of no(2) indicates that the WSH is
          	  currently  waiting for work to perform on behalf of one
          	  of its associated workstation clients. "
        ::= { tuxTwshEntry 14 }   

tuxTwshTaTotacttime OBJECT-TYPE  
        SYNTAX  INTEGER 
        ACCESS  read-only
        STATUS  mandatory   
        DESCRIPTION        
                " Time, in seconds, that the WSH has been active since it
          	  started processing. "
        ::= { tuxTwshEntry 15 }  
   
tuxTwshTaTotidltime OBJECT-TYPE
        SYNTAX  INTEGER
        ACCESS  read-only
        STATUS  mandatory
        DESCRIPTION
                " Time, in seconds, that the WSH has been idle since it
                  started processing. "
        ::= { tuxTwshEntry 16 }
  
tuxTwshTaCurwork OBJECT-TYPE 
        SYNTAX  INTEGER 
        ACCESS  read-only
        STATUS  mandatory 
        DESCRIPTION 
                " Amount of work processed by this WSH since the last WSH
          	  assignment  by  the WSL.  This value is used by the WSL
          	  to load balance new incoming connections amongst a  set
          	  of WSH processes. "
        ::= { tuxTwshEntry 17 }    
 
tuxTwshTaFlowcnt OBJECT-TYPE 
        SYNTAX  INTEGER 
        ACCESS  read-only
        STATUS  mandatory 
        DESCRIPTION 
                " Number of times flow control has  been  encountered  by
          	  this  WSH.  This attribute should be considered only in
          	  relation to recent past values as it  may  wrap  around
          	  during the lifetime of the WSH. "
        ::= { tuxTwshEntry 18 }    

tuxTwshTaNumblockQ OBJECT-TYPE
        SYNTAX  INTEGER
        ACCESS  read-only
        STATUS  mandatory
        DESCRIPTION
                "  Number of times  this  WSH
		   has  been  unable to  enqueue  a message  to  a  local
		   UNIX System message queue due to queue blocking  condi-
		   tions.   This  attribute  should  be considered only in
		   relation to recent past values as it  may  wrap  around
		   during the lifetime of the WSH. "
        ::= { tuxTwshEntry 19 }

tuxTwshTaRcvdByt OBJECT-TYPE 
        SYNTAX  INTEGER
        ACCESS  read-only
        STATUS  mandatory 
        DESCRIPTION   
                " Number  of  bytes  received from the   network  by  this   
	          WSH from  all   of its present and past workstation clients. 
	 	  This  attribute should be   considered  only  in  relation  
		  to recent past  values  as  it may wrap around during the 
		  lifetime of the WSH. "
        ::= { tuxTwshEntry 20 }

tuxTwshTaRcvdNum OBJECT-TYPE 
        SYNTAX  INTEGER
        ACCESS  read-only
        STATUS  mandatory 
        DESCRIPTION   
                " Number  of  TUXEDO  System/T
		  messages   received  from   the network  by  this  WSH
		  from  all  of  its  present  and   past workstation
		  clients.  This   attribute   should   be   considered
		  only  in  relation to recent past values as it may wrap
		  around during the lifetime of the WSH. "
        ::= { tuxTwshEntry 21 }
 
tuxTwshTaSentByt OBJECT-TYPE 
        SYNTAX  INTEGER
        ACCESS  read-only
        STATUS  mandatory 
        DESCRIPTION   
                " Number of bytes sent to the network by this WSH to all of  
	 	  its present and past workstation clients.  This attribute  
		  should be considered only in relation to recent past values  
		  as it may wrap around during the lifetime of the WSH. "
        ::= { tuxTwshEntry 22 }
 
tuxTwshTaSentNum OBJECT-TYPE 
        SYNTAX  INTEGER
        ACCESS  read-only
        STATUS  mandatory 
        DESCRIPTION   
                " Number  of  TUXEDO  System/T
		  messages sent to the network by this WSH to all of its 
		  present and past workstation clients.  This  attribute   
		  should be considered only in relation to recent past 
		  values as it may wrap  around during the lifetime of the 
		  WSH. "
        ::= { tuxTwshEntry 23 }
 

-- *****************************************************************
--- tuxTwslTbl group
--- The tuxTwslTbl table represents configuration and runtime  attri-
--- butes  of  WSL  server  processes  configured  to manage /WS
--- groups.  These attribute values  identify  and  characterize
--- /WS  specific  configuration  attributes  for  WSL  tuxTsrvrTbl
--- objects within the application.
-- *****************************************************************

tuxTwslTbl OBJECT-TYPE
        SYNTAX  SEQUENCE OF TuxTwslEntry
        ACCESS  not-accessible
        STATUS  mandatory
        DESCRIPTION
                " A table which represents runtime attributes of WSL
                 server processes."
        ::= { tuxWsmib 2 }

tuxTwslEntry OBJECT-TYPE
        SYNTAX  TuxTwslEntry
        ACCESS  not-accessible
        STATUS  mandatory
        DESCRIPTION
                " This object depicts one row (corresponding to one
                 workstation listener) in the Twsl table.
    		 Row Creation in tuxTwslTbl:
		 ===========================
	         The essential attributes that need to be provided are 
	   	 tuxTwslTaSrvGrp, tuxTwslTaSrvId and tuxTwslTaNaddr."
        INDEX   { tuxTwslTaGrpNo, tuxTwslTaSrvId }
        ::= { tuxTwslTbl 1 }
 
TuxTwslEntry ::= SEQUENCE {
        tuxTwslTaSrvGrp
                DisplayString,
        tuxTwslTaSrvId
                INTEGER,
        tuxTwslTaGrpNo
                INTEGER,
        tuxTwslTaState
                INTEGER,
        tuxTwslTaLmid
                DisplayString,
        tuxTwslTaPid
                INTEGER,
        tuxTwslTaDevice
                DisplayString,
        tuxTwslTaNaddr
                DisplayString,
        tuxTwslTaWshName
                DisplayString,
        tuxTwslTaMinHandlers
                INTEGER,
        tuxTwslTaMaxHandlers
                INTEGER,
        tuxTwslTaMultiplex
                INTEGER,
        tuxTwslTaMaxIdleTime
                INTEGER,
        tuxTwslTaMaxInitTime
                INTEGER,
        tuxTwslTaClOpt
                DisplayString,
        tuxTwslTaEnvFile
                DisplayString,
        tuxTwslTaGrace
                INTEGER,
	tuxTwslTaMaxGen
                INTEGER,
        tuxTwslTaRcmd
                DisplayString,
        tuxTwslTaRestart
                INTEGER,
        tuxTwslTaSequence
                INTEGER,
        tuxTwslTaCurHandlers
                INTEGER,
        tuxTwslTaHwHandlers
                INTEGER,
        tuxTwslTaWsProto
                INTEGER,
        tuxTwslTaSuspended
                INTEGER,
        tuxTwslTaViewRefresh
                INTEGER,
        tuxTwslTaKeepAlive
                INTEGER,
        tuxTwslTaNetTimeOut
                INTEGER
        }


tuxTwslTaSrvGrp OBJECT-TYPE
        SYNTAX  DisplayString ( SIZE(1..30) )
        ACCESS  read-write	-- writable only in row creation.
        STATUS  mandatory
        DESCRIPTION
                " Logical name of the server group.  Server  group  names
          	  cannot contain an asterisk (*), comma, or colon. 
		  NOTE: This object can be updated only during row creation."
        ::= { tuxTwslEntry 1 }

tuxTwslTaSrvId OBJECT-TYPE 
        SYNTAX  INTEGER (1..30001)
        ACCESS  read-write	-- writable only in row creation.
        STATUS  mandatory 
        DESCRIPTION 
                " Unique (within the server group) server  identification
          	  number.
		  NOTE: This object can be updated only during row creation."
        ::= { tuxTwslEntry 2 }

tuxTwslTaGrpNo OBJECT-TYPE
        SYNTAX  INTEGER (1..30001)
        ACCESS  read-only
        STATUS  mandatory 
        DESCRIPTION 
                " Group number associated with this servers group. "
        ::= { tuxTwslEntry 3 }
 
tuxTwslTaState OBJECT-TYPE 
        SYNTAX  INTEGER {
		active(1),
		inactive(2),
		migrating(3),
		cleaning(4),
		restarting(5),
		suspended(6),
		partitioned(7),
		dead(8),
		invalid(9)
	}
        ACCESS  read-write
        STATUS  mandatory  
        DESCRIPTION  
                " State for the WSL server within the  application.   Any
          	  state  defined  for the tuxTsrvrTbl group may be returned 
		  or set as indicated "
        ::= { tuxTwslEntry 4 } 
  
tuxTwslTaLmid OBJECT-TYPE 
        SYNTAX  DisplayString ( SIZE (1..30) ) 
        ACCESS  read-only
        STATUS  mandatory  
        DESCRIPTION  
                " Current logical machine on which the server is running. "
        ::= { tuxTwslEntry 5 } 
  
tuxTwslTaPid OBJECT-TYPE  
        SYNTAX  INTEGER
        ACCESS  read-only
        STATUS  mandatory   
        DESCRIPTION   
                " Native operating system process identifier for the  WSL
          	  server. "
        ::= { tuxTwslEntry 6 }

tuxTwslTaDevice OBJECT-TYPE   
        SYNTAX  DisplayString ( SIZE (0..78) )
        ACCESS  read-write
        STATUS  mandatory    
        DESCRIPTION    
                " Device name to be used by the WSL process to access the
          	  network.  This is a required value for access to a net-
          	  work via a  TLI-based  TUXEDO  System/T  binary.   This
          	  attribute   is  not  needed  for  sockets-based  TUXEDO
          	  System/T binaries. "
        ::= { tuxTwslEntry 7 } 

tuxTwslTaNaddr OBJECT-TYPE   
        SYNTAX  DisplayString ( SIZE(1..256) )
        ACCESS  read-write
        STATUS  mandatory    
        DESCRIPTION    
                " Specifies the complete network address to  be  used  by
          	  the  WSL process as its listening address.  The listen-
          	  ing address for a WSL is the means by which it is  con-
          	  tacted by workstation client processes participating in
          	  the application.

          	  If string has the form  ``0xhex-digits''  or  ``\\xhex-
          	  digits'',  it  must contain an even number of valid hex
          	  digits.  These forms are translated internally  into  a
          	  character  array containing the hexadecimal representa-
          	  tions of the string specified. "
        ::= { tuxTwslEntry 8 } 
 
tuxTwslTaWshName OBJECT-TYPE    
        SYNTAX  DisplayString ( SIZE (1..256) )
        ACCESS  read-write
        STATUS  mandatory     
        DESCRIPTION      
                " The  name  of  the  executable  providing   workstation
          	  handler  services  for  this workstation listener.  The
          	  default value for this is WSH which corresponds to  the
          	  system   provided   workstation  handler.   Workstation
          	  handlers  may   be   customized   using   the   command
          	  buildwsh. "
        ::= { tuxTwslEntry 9 }    

tuxTwslTaMinHandlers OBJECT-TYPE     
        SYNTAX  INTEGER (0..256)
        ACCESS  read-write
        STATUS  mandatory      
        DESCRIPTION          
                " The minimum number of handlers that should be available
          	  in  conjunction  with  this WSL at any given time.  The
          	  WSL will start this many WSHs  immediately  upon  being
          	  activated and will not deplete the supply of WSHs below
          	  this number until the administrator issues  a  shutdown
          	  to the WSL.  Modifications to this attribute for a run-
          	  ning WSL may cause additional handlers to be activated. "
        ::= { tuxTwslEntry 10 }

tuxTwslTaMaxHandlers OBJECT-TYPE      
        SYNTAX  INTEGER (0..32766)
        ACCESS  read-write
        STATUS  mandatory      
        DESCRIPTION           
                " The maximum number of handlers that should be available
          	  in  conjunction  with  this  WSL  at  any  given  time.
          	  Handlers are started as necessary to meet the demand of
          	  workstation  clients  attempting  to access the system.
          	  This attribute must be greater than  or  equal  to  the
          	  setting for the minumum number of handlers. "
        ::= { tuxTwslEntry 11 } 
 
tuxTwslTaMultiplex OBJECT-TYPE       
        SYNTAX  INTEGER (0..32767)
        ACCESS  read-write
        STATUS  mandatory       
        DESCRIPTION           
                " Maximum number of clients that are to be  supported  by
          	  any one handler process concurrently. "
        ::= { tuxTwslEntry 12 }  
  
tuxTwslTaMaxIdleTime OBJECT-TYPE       
        SYNTAX  INTEGER 
        ACCESS  read-write
        STATUS  mandatory       
        DESCRIPTION           
                " Maximum amount of time, in minutes, that a  workstation
          	  client  is permitted to be idle before it will be abor-
          	  tively  disconnected  from  the  application   by   the
          	  handler.   A  value  of  0 allows clients to be idle as
          	  long as they wish without being timed out."
        ::= { tuxTwslEntry 13 }  
  
tuxTwslTaMaxInitTime OBJECT-TYPE       
        SYNTAX  INTEGER 
        ACCESS  read-write
        STATUS  mandatory       
        DESCRIPTION           
                " The minimum number of seconds that  should  be  allowed
          	  for  a  workstation  client  to complete initialization
          	  processing through the WSH before being  timed  out  by
          	  the WSL."
        ::= { tuxTwslEntry 14 }  
 
tuxTwslTaClOpt OBJECT-TYPE       
        SYNTAX  DisplayString ( SIZE (0..128) ) 
        ACCESS  read-write
        STATUS  mandatory       
        DESCRIPTION            
                " Command line options to be passed to WSL server when it
          	  is  activated.   See  the  servopts(5)  manual page for
          	  details.  Limitations: Runtime  modifications  to  this
          	  attribute will not affect a running WSL server.  Server
          	  specific options (i.e., those after a double-dash `--')
          	  may not be set and will not be returned. "
        ::= { tuxTwslEntry 15 }  
 
tuxTwslTaEnvFile OBJECT-TYPE       
        SYNTAX  DisplayString ( SIZE (0..256) ) 
        ACCESS  read-write
        STATUS  mandatory       
        DESCRIPTION            
                " WSL   server   specific    environment    file.     See
          	  tuxTmachineEnvFile  for  a complete discussion of how
          	  this file is used to modify the  environment.   Limita-
          	  tion:  Runtime modifications to this attribute will not
          	  affect a running WSL server."
        ::= { tuxTwslEntry 16 }  
 
tuxTwslTaGrace OBJECT-TYPE       
        SYNTAX  INTEGER 
        ACCESS  read-write
        STATUS  mandatory       
        DESCRIPTION            
                " The  period  of  time,  in  seconds,  over  which   the
          	  tuxTWslMaxgen limit applies.  This attribute is mean-
          	  ingful only for restartable WSL servers, i.e.,  if  the
          	  tuxTWslRestart  attribute is set to `yes(1)'. When a res-
          	  tarting server would exceed the tuxTwslMaxGen limit but the
          	  tuxTwslGrace  period  has  expired,  the  system resets the
          	  current generation (tuxTsrvrGeneration)  to  1  and
          	  resets the initial boot time (tuxTsrvrTimeStart) to
          	  the current time.  A value  of  0  for  this  attribute
          	  indicates  that  the  WSL  server should always be res-
          	  tarted."
        ::= { tuxTwslEntry 17 }  
 
tuxTwslTaMaxGen OBJECT-TYPE       
        SYNTAX  INTEGER  (0..256)
        ACCESS  read-write
        STATUS  mandatory       
        DESCRIPTION            
                " Number of generations allowed  for  a  restartable  WSL
          	  server  (tuxTWslRestart  ==  yes(1) )  over the specified
          	  grace period (tuxTwslGrace).  The initial  activation
          	  of  the  WSL  server  counts as one generation and each
          	  restart also counts as one.  Processing after the  max-
          	  imum  generations  is  exceeded is discussed above with
          	  respect to tuxTwslGrace."
        ::= { tuxTwslEntry 18 }  
 
tuxTwslTaRcmd OBJECT-TYPE       
        SYNTAX  DisplayString ( SIZE(0..256) ) 
        ACCESS  read-write
        STATUS  mandatory       
        DESCRIPTION            
                " Application specified command to be executed in  paral-
          	  lel  with  the system restart of an application server.
          	  This command must be an executable file in  the  native
          	  operating system. "
        ::= { tuxTwslEntry 19 }  
 
 
tuxTwslTaRestart OBJECT-TYPE
        SYNTAX  INTEGER {
		yes(1),
		no(2)
		} 
        ACCESS  read-write
        STATUS  mandatory       
        DESCRIPTION            
                " Restartable ( yes(1) ) or non-restartable (`no(2)') WSL  
		  server.  If  server migration is specified for this server 
		  group (tuxTdomainOptions = migrate(2)  & tuxTGroupLmid w/
          	  alternate  site),  then  this  attribute must be set to
          	  yes(1) . "
        ::= { tuxTwslEntry 20 }      
 
tuxTwslTaSequence OBJECT-TYPE
        SYNTAX  INTEGER  (1..9999)
        ACCESS  read-write
        STATUS  mandatory       
        DESCRIPTION            
                " Specifies when this server should be booted (tmboot(1))
          	  or  shutdown (tmshutdown(1)) relative to other servers.
          	  If two servers are given the same sequence  number,  it
          	  is  possible for tmboot(1) to boot them in parallel and
          	  for tmshutdown(1) to shut them down in parallel.  tuxTwslTbl
          	  instances added without a tuxTwslSequence attribute specified
          	  or with an invalid value will have  one  generated  for
          	  them  that  is  10,000  or  more and is higher than any
          	  other automatically selected  default  value.   Servers
          	  are booted by tmboot(1) in increasing order of sequence
          	  number and  shutdown  by  tmshutdown(1)  in  decreasing
          	  order.   Runtime modifications to this attribute affect
          	  only tmboot(1) and tmshutdown(1) and  will  affect  the
          	  order  in  which  running  servers may be shutdown by a
          	  subsequent invocation of tmshutdown(1). "
        ::= { tuxTwslEntry 21 }      
 
tuxTwslTaCurHandlers OBJECT-TYPE
        SYNTAX  INTEGER
        ACCESS  read-only
        STATUS  mandatory       
        DESCRIPTION            
                " Number of currently  active  handlers  associated  with
          	  this WSL. "
        ::= { tuxTwslEntry 22 }      
 
tuxTwslTaHwHandlers OBJECT-TYPE
        SYNTAX  INTEGER
        ACCESS  read-only
        STATUS  mandatory       
        DESCRIPTION            
                " Maximum number of currently active handlers  associated
          	  with this WSL at any one time. "
        ::= { tuxTwslEntry 23 }      
 
tuxTwslTaWsProto OBJECT-TYPE
        SYNTAX  INTEGER
        ACCESS  read-only
        STATUS  mandatory       
        DESCRIPTION            
                " The TUXEDO System/T /WS  protocol  version  number  for
          	  this  /WS  group.   Note that /WS clients connecting to
          	  this group may themselves  have  a  different  protocol
          	  version number associated with them. "
        ::= { tuxTwslEntry 24 }      
 
tuxTwslTaSuspended OBJECT-TYPE
        SYNTAX  INTEGER {
		new(1),
		all(2),
		none(3)
		}
        ACCESS  read-write
        STATUS  mandatory       
        DESCRIPTION            
                " A value of new(1) indicates that new incoming clients  may
          	  not  connect  through  this tuxTwslTbl instance.  A value of 
		  all(2) indicates that workstation clients already connected 
		  to the  application  through  this WSL have been SUSPENDED
          	  (see tuxTclientState) in addition to disallowing new incoming
          	  connections.  A value of none(3) indicates that no suspen-
          	  sion characteristics are in effect. "
        ::= { tuxTwslEntry 25 }      
 
tuxTwslTaViewRefresh OBJECT-TYPE
        SYNTAX  INTEGER {
		yes(1),
		no-value-returned(2)
		} 
        ACCESS  read-write
        STATUS  mandatory       
        DESCRIPTION            
                " Setting a value of yes(1) will cause all active WSHs in  the
          	  /WS group to refresh their VIEW buffer type cache. A get req-
		 uest on this object always returns no(2) and does not mean
		 anything, This object has meaning only for SET requests."
        ::= { tuxTwslEntry 26 }      

tuxTwslTaKeepAlive OBJECT-TYPE
        SYNTAX  INTEGER {
		client(1),
		handler(2),
		both(3),
		none(4),
		not-available(5)
		}
        ACCESS  read-write
        STATUS  mandatory       
        DESCRIPTION            
                " Network 'keep-alive' option will be configured for the client
		  , the handler, both the handler and client or not on either
		 side of the connection. Changing this value affects only conn-
		 ections established in the future.
		 SUPPORT: Tuxedo 6.4 or later only. "
        ::= { tuxTwslEntry 28 }      

tuxTwslTaNetTimeOut OBJECT-TYPE
        SYNTAX  INTEGER (0..35204650)
        ACCESS  read-write
        STATUS  mandatory       
        DESCRIPTION            
                " Minimum number of seconds that should be allowed for a work-
		  station client to wait for receiving a response from WSL/WSH.
		  A value of 0 indicates no network time-out. Changing this
		  value affects only connections established in the future.
		  SUPPORT: Tuxedo 6.4 or later only.(-1 is returned if the
			   object is not available.)"
        ::= { tuxTwslEntry 29 }      

--*****************************************************************************
-- tuxEvents 
-- This group represents a MIB table each for different type of event 
-- subscriptions available in the TUXEDO system. 
-- To receive data for Event Subscriptions for system and user events TMSYSEVT
-- and TMUSREVT (respectively) servers must be running.
-- TMSYSEVT is needed in any case by Agent Connection to be able to forward 
-- system events as SNMP traps. If only TMSYSEVT is running only system event
-- subscription data is returned, else no data is returned.
--*****************************************************************************

--*****************************************************************************
-- tuxEventClient group
-- This represents a set  of  subscriptions registered  with the Event Broker 
-- for client-based notification.  When an event is detected, it  is  compared  
-- to  each tuxEventClient  instance.  If the event name matches the value
-- in the event expression and the optional filter rule is true,  then
-- the  event  buffer is sent to the specified client's unsolicited message 
-- handling routine.
--*****************************************************************************
tuxEventClient	OBJECT IDENTIFIER ::= 	{ tuxEvents 1 }
	
tuxEventClientTbl OBJECT-TYPE
	SYNTAX SEQUENCE OF TuxEventClientEntry
	ACCESS not-accessible
	STATUS mandatory
	DESCRIPTION
		  " This is the table which represents all client-based notifi-
		    cation events. "
	::= { tuxEventClient 1 }

tuxEventClientEntry OBJECT-TYPE 
        SYNTAX TuxEventClientEntry 
        ACCESS not-accessible 
        STATUS mandatory
        DESCRIPTION 
                  " A row in tuxEventClientTbl. 
		    Row (instance) creation in tuxEventClientTbl:
		    ============================================
		    A set request for a new instance with atleast 
		    tuxEventClientExpr and tuxEventClientId is needed. " 
	INDEX	{ tuxEventClientIndx }
        ::= { tuxEventClientTbl 1 } 

TuxEventClientEntry ::= SEQUENCE {
	tuxEventClientIndx
		INTEGER,
	tuxEventClientExpr
		DisplayString,
	tuxEventClientFilter
		DisplayString,
	tuxEventClientState
		INTEGER,
	tuxEventClientId
		DisplayString
	}
 
tuxEventClientIndx OBJECT-TYPE
        SYNTAX INTEGER
        ACCESS read-only 
        STATUS mandatory
        DESCRIPTION
                  " A running number as the unique identifier for  a row in 
		    the table. " 
        ::= { tuxEventClientEntry 1 }
 
tuxEventClientExpr OBJECT-TYPE
        SYNTAX DisplayString (SIZE(1..255))
        ACCESS read-write	-- writable only in row creation.
        STATUS mandatory
        DESCRIPTION
                  " Event  pattern   expression.    This   expression,   in
          	    recomp(3) format, controls which event names match this
          	    subscription. 
		    NOTE: This object can be updated only during row creation."
        ::= { tuxEventClientEntry 2 }
 
tuxEventClientFilter OBJECT-TYPE
        SYNTAX DisplayString (SIZE(1..255))
        ACCESS read-write	-- writable only in row creation.
        STATUS mandatory
        DESCRIPTION
                  " Event filter expression.  This expression, if  present,
          	    is  evaluated  with respect to the posted buffer's con-
          	    tents.  It must evaluate to TRUE or  this  subscription
          	    is not matched. If the value of this is `-', it means that
		    the filter expression is in binary format.
		    NOTE: This object can be updated only during row creation."
        ::= { tuxEventClientEntry 3 }
 
tuxEventClientState OBJECT-TYPE
        SYNTAX INTEGER {
		active(1),
		invalid(2)
		}
        ACCESS read-write
        STATUS mandatory
        DESCRIPTION
                  " 
          GET: active(1)
               A GET operation will retrieve configuration infor-
               mation for the matching tuxEventClientTbl row(s). 

          SET: 
               A SET operation will update configuration informa-
               tion for the row in tuxEventClientTbl .  The following
               states indicate the meaning of a tuxEventClientState set 
	       in a SET request.  States not listed may not be set.

         invalid(2) 
		  Delete row .   Successful  return leaves the  row  
		  in the invalid(2) state. "
        ::= { tuxEventClientEntry 4 }
 
tuxEventClientId OBJECT-TYPE
        SYNTAX DisplayString (SIZE(1..78))
        ACCESS read-write	-- writable only in row creation.
        STATUS mandatory
        DESCRIPTION
                  " Send an unsolicited notification message to this client
          	    when a matching event is detected.
                    NOTE: This object can be updated only during row creation."
        ::= { tuxEventClientEntry 5 }
 

--- ***************************************************************************
--- tuxEventCommand group
--- This represents a set of  subscriptions
---  registered  with  the Event Broker that trigger execution of
---  system commands.
---
---  When  an  event  is  detected,  it  is  compared   to   each
---  row in this table.  If the event name matches the value
---  in the event expression and the optional filter rule is true,  then
---  the  event  buffer  is  formatted and passed to the system's
---  command interpreter.
---
--- Create a new Row:
--- To create a new instance of tuxEventCmdTbl the user must specify atleast
--- tuxEventCmdExpr and tuxTEventCmd. All objects except tuxEventCmdState can
--- be updated only during creation of a new instance.
--- ***************************************************************************

tuxEventCommand OBJECT IDENTIFIER ::= { tuxEvents 2 }

tuxEventCmdTbl OBJECT-TYPE
        SYNTAX SEQUENCE OF TuxEventCmdEntry
        ACCESS not-accessible
        STATUS mandatory
        DESCRIPTION
                  " This is the table which represents all command-based 
                    events. "
        ::= { tuxEventCommand 1 }

tuxEventCmdEntry OBJECT-TYPE
        SYNTAX TuxEventCmdEntry
        ACCESS not-accessible
        STATUS mandatory
        DESCRIPTION
                  " A row in tuxEventCmdTbl. 
		    Creation of new instance:
		    ========================
		    A set request for a new instance with atleast 
		    tuxEventCmdExpr and tuxEventCmd is required."
        INDEX   { tuxEventCmdIndx }
        ::= { tuxEventCmdTbl 1 }
 
TuxEventCmdEntry ::= SEQUENCE {
        tuxEventCmdIndx
                INTEGER,
        tuxEventCmdExpr
                DisplayString,
        tuxEventCmdFilter
                DisplayString,
        tuxEventCmdState
                INTEGER,
        tuxEventCmd
                DisplayString
        }
 
tuxEventCmdIndx OBJECT-TYPE
        SYNTAX INTEGER
        ACCESS read-only
        STATUS mandatory
        DESCRIPTION
                  " A running number as the unique identifier for  a row in
                    the table. "
        ::= { tuxEventCmdEntry 1 }
 
tuxEventCmdExpr OBJECT-TYPE
        SYNTAX DisplayString (SIZE(1..255))
        ACCESS read-write	-- writable only in row creation.
        STATUS mandatory
        DESCRIPTION
                  " Event  pattern   expression.    This   expression,   in
          	    recomp(3) format, controls which event names match this
          	    subscription.

                    NOTE: This object can be updated only during row creation."
        ::= { tuxEventCmdEntry 2 }
 
tuxEventCmdFilter OBJECT-TYPE
        SYNTAX DisplayString (SIZE(1..255))
        ACCESS read-write	-- writable only in row creation.
        STATUS mandatory
        DESCRIPTION
                  " Event filter expression.  This expression, if  present,
          is  evaluated  with respect to the posted buffer's con-
          tents.  It must evaluate to TRUE or  this  subscription
          is not matched. If the value of the filter is `-' that means that
	  the filter is in a binary format.

          NOTE: This object can be updated only during row creation."
        ::= { tuxEventCmdEntry 3 }
 
tuxEventCmdState OBJECT-TYPE
        SYNTAX INTEGER {
		active(1),
		invalid(2)
		}
        ACCESS read-write
        STATUS mandatory
        DESCRIPTION
                  " GET: active(1)
                A GET operation will retrieve configuration information for
                the tuxEventCmdTbl instance(s).

           SET: invalid(2)
                A SET operation will update configuration information for
                the tuxEventCmdTbl instance.  The following states indicate
                the meaning of a tuxEventCmdState set in a SET request.  States
		not listed may not be set.

                invalid(2) Delete tuxEventCmdTbl instance.  Successful return
                          leaves the object in the invalid(2) state."
        ::= { tuxEventCmdEntry 4 }
 
tuxEventCmd OBJECT-TYPE
        SYNTAX DisplayString  (SIZE(1..255))
        ACCESS read-write	-- writable only in row creation.
        STATUS mandatory
	DESCRIPTION
		   " Execute this system command when an event matching this
                    object  is  detected.   For  UNIX System platforms, the
                    command is executed in the background using system(3).
                    NOTE: This object can be updated only during row creation."
        ::= { tuxEventCmdEntry 5 }

--- ************************************************************************ 
--- tuxEventQueue group
--- This represents a  set  of  subscriptions
---  registered  with  the Event Broker for queue-based notifica-
---  tion.
---
---  When  an  event  is  detected,  it  is  compared   to   each
---  tuxEventQueue  instance.   If the event name matches the value
---  in event expresssion and the optional filter rule is true,  then
---  the event buffer is stored in the specified reliable queue.
--- ************************************************************************ 
tuxEventQueue OBJECT IDENTIFIER ::= { tuxEvents 3 }

tuxEventQueTbl OBJECT-TYPE
        SYNTAX SEQUENCE OF TuxEventQueEntry
        ACCESS not-accessible
        STATUS mandatory
        DESCRIPTION
                  " This is the table which represents all queue-based
                    events. "
        ::= { tuxEventQueue 1 }

tuxEventQueEntry OBJECT-TYPE
        SYNTAX TuxEventQueEntry
        ACCESS not-accessible
        STATUS mandatory
        DESCRIPTION
                  " A row in tuxEventQueTbl. 		
		    Creation of new row(instance):
		    ============================
		   A set request for a new instance with atleast tuxEventQueExpr		   , tuxEventQspace and tuxEventQname is required. "
        INDEX   { tuxEventQueIndx }
        ::= { tuxEventQueTbl 1 }

TuxEventQueEntry ::= SEQUENCE {
        tuxEventQueIndx
                INTEGER,
        tuxEventQueExpr
                DisplayString,
        tuxEventQueFilter
                DisplayString,
        tuxEventQueState
                INTEGER,
        tuxEventQspace
                DisplayString,
	tuxEventQname
		DisplayString,
	tuxEventQctlQtop
		INTEGER,
	tuxEventQctlBeforeMsgid
		INTEGER,
	tuxEventQctlQtimeAbs
		INTEGER,
	tuxEventQctlQtimeRel
		INTEGER,
	tuxEventQctlDeqTime
		INTEGER,
	tuxEventQctlPrior
		INTEGER,
	tuxEventQctlMsgId
		DisplayString,
	tuxEventQctlCorrId
		DisplayString,
	tuxEventQctlReplyQ
		DisplayString,
	tuxEventQctlFailQ
		DisplayString,
	tuxEventPersist
		INTEGER,
	tuxEventTran
		INTEGER
	}

tuxEventQueIndx OBJECT-TYPE
        SYNTAX INTEGER 
        ACCESS read-only
        STATUS mandatory
        DESCRIPTION
                  " Running number which is unique identifier for an event in
		    this table . " 
        ::= { tuxEventQueEntry 1 }

tuxEventQueExpr OBJECT-TYPE 
        SYNTAX DisplayString (SIZE(1..255)) 
        ACCESS read-write	-- writable only in row creation.
        STATUS mandatory
        DESCRIPTION    
                  " Event  pattern   expression.    This   expression,   in
          	   recomp(3) format, controls which event names match this
          	   subscription.
		  NOTE: This object can be updated only during row creation."
        ::= { tuxEventQueEntry 2 }
 
tuxEventQueFilter OBJECT-TYPE 
        SYNTAX DisplayString (SIZE(1..255)) 
        ACCESS read-write	-- writable only in row creation.
        STATUS mandatory
        DESCRIPTION    
                  " Event filter expression.  This expression, if  present,
          	   is  evaluated  with respect to the posted buffer's con-
          	   tents.  It must evaluate to TRUE or  this  subscription
          	   is not matched. If the value of this object is `-' that 
		   means the filter is in binary format.
		  NOTE: This object can be updated only during row creation."
        ::= { tuxEventQueEntry 3 }
 
tuxEventQueState OBJECT-TYPE 
        SYNTAX INTEGER  {
		active(1),
		invalid(2)
		}
        ACCESS read-write
        STATUS mandatory
        DESCRIPTION    
                  " 
          GET: active(1)
               A GET operation will retrieve configuration infor-
               mation for the matching tuxEventQueue row(s).

          SET: 
               A SET operation will update configuration informa-
               tion  for the tuxEventQueue instance.  The following
               states indicate the meaning of a tuxTEventQueState set 
	       in a SET request.  States not listed may not be set.

               invalid(2) Delete tuxEventQueue row.  Successful
                         return  leaves the object in the INValid
                         state."
        ::= { tuxEventQueEntry 4 }
 
tuxEventQspace OBJECT-TYPE 
        SYNTAX DisplayString (SIZE(1..15)) 
        ACCESS read-write	-- writable only in row creation.
        STATUS mandatory
        DESCRIPTION    
                  " Enqueue a notification message to a reliable  queue  in
          	    this queue space when a matching event is detected.
		  NOTE: This object can be updated only during row creation."
        ::= { tuxEventQueEntry 5 }
 
tuxEventQname OBJECT-TYPE 
        SYNTAX DisplayString (SIZE(1..15))     
        ACCESS read-write	-- writable only in row creation.
        STATUS mandatory
        DESCRIPTION    
                  " Enqueue a notification message to this  reliable  queue
          	    when a matching event is detected.
		  NOTE: This object can be updated only during row creation."
        ::= { tuxEventQueEntry 6 }

 tuxEventQctlQtop OBJECT-TYPE 
        SYNTAX INTEGER 
        ACCESS read-write	-- writable only in row creation.
        STATUS mandatory
        DESCRIPTION    
                  " This value, if present, is passed in to  tpenqueue(3)'s
          	   TPQCTL  control  structure  to request notification via
          	   the /Q subsystem with the message to be placed  at  the
          	   top of the queue.
		  NOTE: This object can be updated only during row creation."
        ::= { tuxEventQueEntry 7 }
  
 tuxEventQctlBeforeMsgid OBJECT-TYPE  
        SYNTAX INTEGER 
        ACCESS read-write	-- writable only in row creation.
        STATUS mandatory 
        DESCRIPTION     
                  " This value, if present, is passed in to  tpenqueue(3)'s
          	    TPQCTL  control  structure  to request notification via
          	    the /Q subsystem with the message to be placed  on  the
          	    queue ahead of the specified message.
		  NOTE: This object can be updated only during row creation."
        ::= { tuxEventQueEntry 8 }
 
 tuxEventQctlQtimeAbs OBJECT-TYPE  
        SYNTAX INTEGER 
        ACCESS read-write	-- writable only in row creation.
        STATUS mandatory 
        DESCRIPTION     
                  " This value, if present, is passed in to  tpenqueue(3)'s
          	    TPQCTL  control  structure  to request notification via
          	    the /Q subsystem with the message to  be  processed  at
          	    the specified time.
		  NOTE: This object can be updated only during row creation."
        ::= { tuxEventQueEntry 9 }
 
 tuxEventQctlQtimeRel OBJECT-TYPE  
        SYNTAX INTEGER 
        ACCESS read-write	-- writable only in row creation.
        STATUS mandatory 
        DESCRIPTION     
                  " This value, if present, is passed in to  tpenqueue(3)'s
          	    TPQCTL  control  structure  to request notification via
          	    the /Q subsystem with the message to be processed rela-
          	    tive to the dequeue time.
		  NOTE: This object can be updated only during row creation."
        ::= { tuxEventQueEntry 10 }
 
 tuxEventQctlDeqTime OBJECT-TYPE  
        SYNTAX INTEGER 
        ACCESS read-write	-- writable only in row creation.
        STATUS mandatory 
        DESCRIPTION     
                  " This value, if present, is passed in to  tpenqueue(3)'s
          	    TPQCTL control structure.
		  NOTE: This object can be updated only during row creation."
        ::= { tuxEventQueEntry 11 }
 
 tuxEventQctlPrior OBJECT-TYPE  
        SYNTAX INTEGER 
        ACCESS read-write	-- writable only in row creation.
        STATUS mandatory 
        DESCRIPTION     
                  " This value, if present, is passed in to  tpenqueue(3)'s
          	    TPQCTL control structure.
		  NOTE: This object can be updated only during row creation."
        ::= { tuxEventQueEntry 12 }
 
 tuxEventQctlMsgId OBJECT-TYPE  
        SYNTAX DisplayString (SIZE(1..31)) 
        ACCESS read-write	-- writable only in row creation.
        STATUS mandatory 
        DESCRIPTION     
                  " This value, if present, is passed in to  tpenqueue(3)'s
          	    TPQCTL structure.
		  NOTE: This object can be updated only during row creation."
        ::= { tuxEventQueEntry 13 }
 
 tuxEventQctlCorrId OBJECT-TYPE  
        SYNTAX DisplayString (SIZE(1..31)) 
        ACCESS read-write	-- writable only in row creation.
        STATUS mandatory 
        DESCRIPTION     
                  " This value, if present, is passed in to  tpenqueue(3)'s
          	    TPQCTL control structure.
		  NOTE: This object can be updated only during row creation."
        ::= { tuxEventQueEntry 14 }
 
 tuxEventQctlReplyQ OBJECT-TYPE  
        SYNTAX DisplayString (SIZE(1..15)) 
        ACCESS read-write	-- writable only in row creation.
        STATUS mandatory 
        DESCRIPTION     
                  " This value, if present, is passed in to  tpenqueue(3)'s
          	    TPQCTL control structure.
		  NOTE: This object can be updated only during row creation."
        ::= { tuxEventQueEntry 15 }
 
 tuxEventQctlFailQ OBJECT-TYPE  
        SYNTAX DisplayString (SIZE(1..15)) 
        ACCESS read-write	-- writable only in row creation.
        STATUS mandatory 
        DESCRIPTION     
                  " This value, if present, is passed in to  tpenqueue(3)'s
          	    TPQCTL control structure.
		  NOTE: This object can be updated only during row creation."
        ::= { tuxEventQueEntry 16 }
 

tuxEventPersist OBJECT-TYPE
        SYNTAX INTEGER 
        ACCESS read-write	-- writable only in row creation.
        STATUS mandatory 
        DESCRIPTION     
                  " If non-zero, do not cancel  this  subscription  if  the
          	    designated queue is no longer available. 
		  NOTE: This object can be updated only during row creation."
        ::= { tuxEventQueEntry 17 }
 
tuxEventTran OBJECT-TYPE
        SYNTAX INTEGER 
        ACCESS read-write	-- writable only in row creation.
        STATUS mandatory 
        DESCRIPTION     
                  " If non-zero and the client's tppost(3) call is transac-
          	    tional,  include  the tpenqueue(3) call in the client's
          	    transaction.
		  NOTE: This object can be updated only during row creation."
        ::= { tuxEventQueEntry 18 }

 

--- ***************************************************************************
--- tuxEventService Group
--- This represents a set of  subscriptions
---  registered with the Event Broker for service-based notifica-
---  tion.

---  When  an  event  is  detected,  it  is  compared   to   each
---  tuxEventService instance.  If the event name matches the value
---  in the event expression and the optional filter rule is true,  then
---  the  event  buffer  is  sent to the specified TUXEDO service
---  routine.
--- ***************************************************************************

tuxEventService OBJECT IDENTIFIER ::= { tuxEvents 4 }

tuxEventSvcTbl OBJECT-TYPE
        SYNTAX SEQUENCE OF TuxEventSvcEntry
        ACCESS not-accessible
        STATUS mandatory    
        DESCRIPTION    
                  " This is the table which represents all service-based
                    events. "
        ::= { tuxEventService 1 }

tuxEventSvcEntry OBJECT-TYPE
        SYNTAX TuxEventSvcEntry
        ACCESS not-accessible 
        STATUS mandatory    
        DESCRIPTION    
                  " A row in tuxEventSvcTbl. 
		    Creation of a new row (instance):
		    ================================
		    A set request for a new instance with atleast 
		    tuxEventSvcExpr and tuxEventSvcName is required. "
        INDEX   { tuxEventSvcIndx }   
        ::= { tuxEventSvcTbl 1 }  

TuxEventSvcEntry ::= SEQUENCE {
        tuxEventSvcIndx
                INTEGER,
        tuxEventSvcExpr
                DisplayString,
        tuxEventSvcFilter
                DisplayString,
        tuxEventSvcState
                INTEGER,
        tuxEventSvcName
                DisplayString,
        tuxEventSvcPersist
                INTEGER,
        tuxEventSvcTran
                INTEGER
	}

tuxEventSvcIndx OBJECT-TYPE
        SYNTAX INTEGER
        ACCESS read-only 
        STATUS mandatory     
        DESCRIPTION        
                  " A running number which is a unique key for a row in this
		    table. " 
        ::= { tuxEventSvcEntry 1 }     
 
tuxEventSvcExpr OBJECT-TYPE 
        SYNTAX DisplayString (SIZE(1..255))
        ACCESS read-write	-- writable only in row creation.
        STATUS mandatory      
        DESCRIPTION         
                  " Event  pattern   expression.    This   expression,   in
          	    recomp(3) format, controls which event names match this
          	    subscription.
                    NOTE: This object can be updated only during row creation."
        ::= { tuxEventSvcEntry 2 }      

  tuxEventSvcFilter OBJECT-TYPE 
        SYNTAX DisplayString (SIZE(1..255))
        ACCESS read-write	-- writable only in row creation.
        STATUS mandatory      
        DESCRIPTION         
                  " Event filter expression.  This expression, if  present,
          	    is  evaluated  with respect to the posted buffer's con-
          	    tents.  It must evaluate to TRUE or  this  subscription
          	    is not matched. If this is `-' that means the filter is
		    in binary format.
                    NOTE: This object can be updated only during row creation."
        ::= { tuxEventSvcEntry 3 }      
  

tuxEventSvcState OBJECT-TYPE  
        SYNTAX INTEGER {
		active(1),
		invalid(2)
		}
        ACCESS read-write
        STATUS mandatory       
        DESCRIPTION          
                  " 
          GET: active(1)
               A GET operation will retrieve configuration infor-
               mation for the matching tuxEventService instance(s).

          SET: 
               A SET operation will update configuration informa-
               tion  for the tuxEventService instance.  The follow-
               ing states indicate the meaning of a tuxEventSvcState
	       set in  a  SET  request.  States not listed may not be set.

               invalid(2)
		         Delete tuxEventService row.  Success-
                         ful  return  leaves  the  object  in the
                         invalid(2) state. "
	::=  { tuxEventSvcEntry 4 }       

tuxEventSvcName OBJECT-TYPE  
        SYNTAX DisplayString (SIZE(1..15))
        ACCESS read-write	-- writable only in row creation.
        STATUS mandatory       
        DESCRIPTION          
                  " Call this TUXEDO  service  when  a  matching  event  is
          	    detected.
                    NOTE: This object can be updated only during row creation."
        ::= { tuxEventSvcEntry 5 }       

tuxEventSvcPersist OBJECT-TYPE  
        SYNTAX INTEGER
        ACCESS read-write	-- writable only in row creation.
        STATUS mandatory       
        DESCRIPTION          
                  " If non-zero, do not cancel  this  subscription  if  the
          	    tuxEventSvcName service is no longer available.
                    NOTE: This object can be updated only during row creation."
        ::= { tuxEventSvcEntry 6 }       

tuxEventSvcTran OBJECT-TYPE  
        SYNTAX INTEGER
        ACCESS read-write	-- writable only in row creation.
        STATUS mandatory       
        DESCRIPTION           
                  " If non-zero and the client's tppost(3) call is transac-
          	   tional,  include the tuxEventSvcName service call in the
          	   client's transaction.
                   NOTE: This object can be updated only during row creation."
        ::= { tuxEventSvcEntry 7 }
 

--- ***************************************************************************
--- tuxEventUlog group
--- This  represents a set of  subscriptions
---  registered  with  the  Event Broker for writing system user-
---  log(3) messages.
---
---  When  an  event  is  detected,  it  is  compared   to   each
---  tuxEventUlog instance.  If the event name matches the value
---  in the event expression and the optional filter rule is true,  then
---  the  event  buffer is formatted and passed to TUXEDO's user-
---  log(3) function.
---
--- Create a new Row:
--- ================
--- To create a new instance of tuxEventUlogTbl the user must specify atleast
--- tuxEventUlogExpr and tuxTEventUlog. All objects except tuxEventUlogState can
--- be updated only during creation of a new instance.
--- ***************************************************************************

tuxEventUlog OBJECT IDENTIFIER ::= { tuxEvents 5 }
 
tuxEventUlogTbl OBJECT-TYPE
        SYNTAX SEQUENCE OF TuxEventUlogEntry
        ACCESS not-accessible
        STATUS mandatory
        DESCRIPTION
                  " This table represents all userlog based event subscriptions 
		    registered to the TUXEDO Event Broker."
        ::= { tuxEventUlog 1 }
 
tuxEventUlogEntry OBJECT-TYPE
        SYNTAX TuxEventUlogEntry
        ACCESS not-accessible
        STATUS mandatory
        DESCRIPTION
                  " A row in tuxEventUlogTbl. 
		    Creation of a new row (instance):
		    ===============================
		   To create a new instance of tuxEventUlogTbl the user must 
		   specify atleast tuxEventUlogExpr and tuxTEventUlog. All 
		   objects except tuxEventUlogState can be updated only 
		   during creation of a new instance.  "
        INDEX   { tuxEventUlogIndx }
        ::= { tuxEventUlogTbl 1 }
 
TuxEventUlogEntry ::= SEQUENCE {
        tuxEventUlogIndx
                INTEGER,
        tuxEventUlogExpr
                DisplayString,
        tuxEventUlogFilter
                DisplayString,
        tuxEventUlogState
                INTEGER,
        tuxEventUserlog
                DisplayString
        }

tuxEventUlogIndx OBJECT-TYPE 
        SYNTAX INTEGER 
        ACCESS read-only 
        STATUS mandatory    
        DESCRIPTION    
                  " A running number which is unique key in this table. " 
        ::= { tuxEventUlogEntry 1 } 
  
tuxEventUlogExpr OBJECT-TYPE  
        SYNTAX DisplayString (SIZE(1..255)) 
        ACCESS read-write	-- writable only in row creation.
        STATUS mandatory    
        DESCRIPTION     
                  " Event  pattern   expression.    This   expression,   in
          	    recomp(3) format, controls which event names match this
          	    subscription.
                    NOTE: This object can be updated only during row creation."
        ::= { tuxEventUlogEntry 2 }  
   
tuxEventUlogFilter OBJECT-TYPE  
        SYNTAX DisplayString (SIZE(1..255)) 
        ACCESS read-write	-- writable only in row creation.
        STATUS mandatory    
        DESCRIPTION     
                  "  Event filter expression.  This expression, if  present,
          	     is  evaluated  with respect to the posted buffer's con-
          	     tents.  It must evaluate to TRUE or  this  subscription
          	     is not matched. If this is `-' that means the filter is 
		     in binary form.
                    NOTE: This object can be updated only during row creation."
        ::= { tuxEventUlogEntry 3 }  
   
tuxEventUlogState OBJECT-TYPE  
        SYNTAX INTEGER  {
		active(1),
		invalid(2)
		}
        ACCESS read-write
        STATUS mandatory    
        DESCRIPTION     
                  " 
          GET: active(1)
               A GET operation will retrieve configuration infor-
               mation for the matching tuxEventUlog instance(s).

          SET: 
               A SET operation will update configuration informa-
               tion  for the tuxEventUlog instance.  The follow-
               ing states indicate the meaning of a tuxEventUlogState  set
               in  a  SET  request.  States not listed may not be
               set.

               invalid(2)
		         Delete tuxEventUlog row.  Success-
                         ful  return  leaves  the  object  in the
                         invalid(2) state."
        ::= { tuxEventUlogEntry 4 }  
   
tuxEventUserlog  OBJECT-TYPE  
        SYNTAX DisplayString (SIZE(1..255)) 
        ACCESS read-write	-- writable only in row creation.
        STATUS mandatory    
        DESCRIPTION     
                  " Write a userlog(3) message when  a  matching  event  is
          	    detected.
                    NOTE: This object can be updated only during row creation."
        ::= { tuxEventUlogEntry 5 }  
   
--- beaDomainList
--- This MIB group represents all known TUXEDO domains known and being 
--- monitored on a given managed node. Each Agent Connection running on a 
--- managed node supports one row in this table corresponding to the domain
--- it is monitoring.

beaDomainList OBJECT-TYPE
        SYNTAX SEQUENCE OF BeaDomainListEntry
        ACCESS not-accessible
        STATUS mandatory
        DESCRIPTION
      " This MIB group represents all known TUXEDO domains known and 
	being monitored on a given managed node. Each Agent Connection 
	running on a managed node supports one row in this table corresp-
	onding to the domain it is monitoring." 
        ::= { bea 305 }
 
beaDomainListEntry OBJECT-TYPE
        SYNTAX BeaDomainListEntry
        ACCESS not-accessible
        STATUS mandatory
        DESCRIPTION
      " This MIB group represents all known TUXEDO domains known and 
	being monitored on a given managed node. Each Agent Connection 
	running on a managed node supports one row in this table corresp-
	onding to the domain it is monitoring.
	Row Creation: is not allowed in this MIB group. Before starting any
	agent a (minimal) tuxconfig must exist."
        INDEX   { beaDomainKey }
        ::= { beaDomainList 1 }

BeaDomainListEntry ::= SEQUENCE {
        beaDomainKey
                INTEGER,
        beaLogicalAgentName
                DisplayString,
        beaDomainID
                DisplayString,
        beaDomainTuxdir
                DisplayString,
        beaDomainTuxconfig
                DisplayString,
	beaDomainStatus
		INTEGER
        }

beaDomainKey OBJECT-TYPE
        SYNTAX INTEGER (32769..262143)
        ACCESS read-only
        STATUS mandatory
        DESCRIPTION
      " Numeric key for the  well-known  address  in  a  TUXEDO System/T
        bulletin board. In a single processor environment, this key `names'
        the bulletin board.  In a multiple processor or LAN environment, this
        key names the message queue of the DBBL.  In addition,  this  key is
        used as a basis for deriving the names of resources other than the well-
        known address, such  as  the  names for bulletin boards throughout the
        application. "
        ::= { beaDomainListEntry 1 }

beaLogicalAgentName OBJECT-TYPE
        SYNTAX DisplayString (SIZE(1..32))
        ACCESS read-only
        STATUS mandatory
        DESCRIPTION
      " The logical name of the agent as provided in the -l option (NT service
	name in case of Windows NT) when the agent was started. This is the
	agent which is monitoring this domain. Also if there are multiple 
	agent connections running on a managed node, this name needs to be
	appended to the community with an @ sign when sending an SNMP request
	to the agent. e.g. if there are two logical agents say 
	simp_snmpd and bank_snmpd the communities used to query values
	from these agents would be 'public@simp_snmpd' and 
	'public@bank_snmpd' respectively. The component after the @ sign is 		used to identify the agent to which the MIB query is to be sent. 
	NOTE: To run multiple agent connections on the same managed node, 
	they must be started as sub-agents (without -s option) and run along
	with the agent integrator.
	Also this object is passed in the variable binding of all SNMP traps
	generated on behalf of TUXEDO system events." 
        ::= { beaDomainListEntry 2 }

beaDomainID OBJECT-TYPE
        SYNTAX DisplayString (SIZE(1..30))
        ACCESS read-only
        STATUS mandatory
        DESCRIPTION
      " This is the BEA domain identification string for the domain being 
	managed by this agent. This object is optional. "
        ::= { beaDomainListEntry 3 }

beaDomainTuxdir OBJECT-TYPE
        SYNTAX DisplayString (SIZE(1..256))
        ACCESS read-only
        STATUS mandatory
        DESCRIPTION
      " TUXDIR value for the domain being managed by this agent. TUXDIR is the 
	absolute pathname of the directory where the TUXEDO software is found 
	for the master machine."
        ::= { beaDomainListEntry 4 }

beaDomainTuxconfig OBJECT-TYPE
        SYNTAX DisplayString (SIZE(1..256))
        ACCESS read-only
        STATUS mandatory
        DESCRIPTION
      " The absolute location including filename for the configuration file
 	of the domain being managed by this agent.  "
        ::= { beaDomainListEntry 5 }
 
beaDomainStatus OBJECT-TYPE 
        SYNTAX INTEGER {
                active(1),
                inactive(2) 
        } 
        ACCESS read-only
        STATUS mandatory
        DESCRIPTION  
      " This object denotes the current state of the domain being managed. The 
	values and their meainings are same as those of tuxTdomainState. " 
        ::= { beaDomainListEntry 6 }

--- **************************************************************************
--- The following objects of tuxTdomain represent global application attributes 
--- for the domain to which the TUXEDO SNMP agent is currently connected.
--- These  object  values serve to identify, customize, size,
--- secure, and tune a TUXEDO System/T application.  Many of the
--- object  values  represented  here  serve  as  application
--- defaults for other groups represented in this  MIB.   There
--- is  exactly one instance of the tuxTdomain group for each 
--- application.  
--- **************************************************************************


tuxTdomainKey OBJECT-TYPE
     SYNTAX  INTEGER (32769..262143)
     ACCESS  read-write
     STATUS  mandatory
     DESCRIPTION 
               " Numeric key for the  well-known  address  in  a  TUXEDO
          	 System/T   bulletin   board.   In  a  single  processor
          	 environment, this key `names' the bulletin board.  In
          	 a multiple processor or LAN environment, this key names
          	 the message queue of the DBBL.  In addition,  this  key
          	 is  used as a basis for deriving the names of resources
          	 other than the well-known address, such  as  the  names
          	 for bulletin boards throughout the application. "
     ::= { tuxTdomain 1 }

tuxTdomainMaster OBJECT-TYPE
     SYNTAX  DisplayString (SIZE (1..30))
     ACCESS  read-write
     STATUS  mandatory
     DESCRIPTION 
        " Master (LMID1) and backup (LMID2) logical machine iden-
          tifiers.  The master identifier (LMID1) must correspond
          to the local machine for  inactive  applications. Single machine
          mode applications (see tuxTdomainModel below) may set only the
          master logical machine  identifier.   Modifications  to
          this  attribute  value in an active multi-machine  application 
	  (see tuxTdomainModel below) have the following semantics:
 
          Assuming current active master LMID A,  current  backup
          master LMID B, and secondary LMIDs C, D, ...., the fol-
          lowing scenarios  define  the  semantics  of  permitted
          changes to this variable in a running MP mode
          application.
          A,B -> B,A - Master migration from A to B.  A,B ->  A,C
          - Change backup master LMID designation to C.
 
          Note that master migration may  be  either  orderly  or
          partitioned.   Orderly  migration  takes place when the
          master machine is  ACTive  and  reachable.   Otherwise,
          partitioned  migration  takes  place.   All newly esta-
          blished or reestablished network connections will  ver-
          ify  that  the two sites connecting share a common view
          of where the master machine is.  Otherwise, the connec-
          tion  will  be  refused  and an appropriate log message
          generated.
          The master and backup machines in an ACTive application
	  must  always  have  a  TUXEDO  System/T  release number
          greater than or equal to all other machines  active  in
          the  application.   The master and backup machines must
          be of the same release.  Modifications to the tuxTdomainMaster
          attribute must preserve this relationship. "
     ::= { tuxTdomain 2 }

tuxTdomainModel OBJECT-TYPE
     SYNTAX  INTEGER {
			single-machine(1),
			multi-machine(2)
		}
     ACCESS  read-write
     STATUS  mandatory
     DESCRIPTION 
               " Configuration type.  single-machine(1)  specifies  a  single  
		 machine configuration;  only one tuxTmachineTable object may 
		 be specified.  multi-machine(2) specifies a multi-machine or  
		 network  configuration;  it must be specified if a networked 
		 application is being defined. "
     ::= { tuxTdomain 3 }

tuxTdomainState OBJECT-TYPE
     SYNTAX  INTEGER {
			active(1),
			inactive(2),
			forcible-inactive(3)
		}
     ACCESS  read-write
     STATUS  mandatory
     DESCRIPTION 
               " GET:
               A GET operation will  retrieve  configuration  and
               runtime  information for the tuxTdomain group.  The
               following  states  indicate  the  meaning   of   a
               tuxTdomainState  returned  in  response to a GET request.
               States not listed will not be returned.
 
               active(1)    tuxTdomain group defined and the  mas-
                            ter machine is active.
 
               inactive(2)  tuxTdomain group defined and  applica-
                            tion is inactive.
 
          SET: 
               A SET operation will update configuration and run-
               time  information  for  the  tuxTdomain group.  The
               following  states  indicate  the  meaning   of   a
               tuxTdomainState set in a SET request.  States not listed
               may not be set.

               active(1)    Activate   administrative   processes
                            (DBBL,   BBL,  etc.)  on  the  master
                            machine.
                            State  change  allowed  only when in the 
			    inactive(2) state.  Successful return leaves 
		   	    the object  in  the active(1) state.

               inactive(2)  Deactivate  administrative  processes (DBBL, BBL etc.)
 			    on the master machine. This change  allowed  only 
			    in the active(1) state. Successful return leaves the 
			    domain in the inactive(2) state. To do complete 
			    shutdown of the application first make all groups 
			    inactive (see tuxTgroupState).
			    This transition fails if any application servers or
			    clients are still attached to the domain. To ignore
			    any running clients or application servers use 
			    forcible-inactive(3) as explained below ...

               forcible-inactive(3)
		            Forcibly deactivate administrative and application
			    processes on the master machine. Attached clients
                            and servers will be  ignored  for the purpose of
                            determining if shutdown should be allowed. State 
			    change allowed only when in the active(1) state. 
			    Successful return leaves the domain in the inac-
                            tive(2) state. You may need to restart any clients
			    before they can be used to process services after
			    this transition.
			    Note: Forcible shutdown works only in case of
			    single-machine applications."
     ::= { tuxTdomain 4 }

tuxTdomainID OBJECT-TYPE
     SYNTAX  DisplayString (SIZE (0..30))
     ACCESS  read-write
     STATUS  mandatory
     DESCRIPTION 
               " Domain identification string. "
     ::= { tuxTdomain 5 }

tuxTdomainUID OBJECT-TYPE
     SYNTAX  INTEGER
     ACCESS  read-write
     STATUS  mandatory
     DESCRIPTION 
               " Default attribute setting for newly configured  objects
		 in tuxTmachineTable .
          	 Limitation: Changes to this  attribute  do  not  affect
          	 active or already configured tuxTmachineTable instances. "
     ::= { tuxTdomain 7 }

tuxTdomainGID OBJECT-TYPE
     SYNTAX  INTEGER
     ACCESS  read-write
     STATUS  mandatory
     DESCRIPTION 
               " Default attribute setting for newly configured  objects
          	 in the tuxTmachineTable group.
          	 Limitation: Changes to this  attribute  do  not  affect
          	 active or already configured tuxTmachineTable instances. "
     ::= { tuxTdomain 8 }

tuxTdomainPerm OBJECT-TYPE
     SYNTAX  DisplayString (SIZE(4))
     ACCESS  read-write
     STATUS  mandatory
     DESCRIPTION 
               " Default attribute setting for newly configured  objects
          	 in the tuxTmachineTable group.
		 Format: 0ddd, where d is a number 0 through 7. 
          	 Limitation: Changes to this  attribute  do  not  affect
          	 active or already configured tuxTmachineTable instances. "
     ::= { tuxTdomain 9 }

tuxTdomainMask OBJECT-TYPE
     SYNTAX  DisplayString (SIZE(1..9))	    -- valid values: 0 thru 0777
     ACCESS  read-write
     STATUS  mandatory
     DESCRIPTION 
               " Attribute access mask.  User type/access mode  combina-
          	 tions  specified by this attribute value will no longer
          	 be allowed for all class/attribute combinations defined
          	 in  this  manual  page.  For example, a setting of 0003
          	 disallows all updates to users other than the  adminis-
          	 trator or the operator. The value of this object should
	 	 be provided as an octal number - 0 thru 0777"
     ::= { tuxTdomain 10 }

tuxTdomainMaxAccessers OBJECT-TYPE
     SYNTAX  INTEGER (1..32767)
     ACCESS  read-write
     STATUS  mandatory
     DESCRIPTION 
               " Default attribute setting for newly configured  instances
          	 in the tuxTmachineTable group.
          	 Limitation: Changes to this  attribute  do  not  affect
          	 active or already configured tuxTmachineTable instances. "
     ::= { tuxTdomain 11 }

tuxTdomainMaxConv OBJECT-TYPE
     SYNTAX  INTEGER (0..32767)
     ACCESS  read-write
     STATUS  mandatory
     DESCRIPTION 
               " Default attribute setting for newly configured  instances
          	 in the tuxTmachineTable group.
          	 Limitation: Changes to this  attribute  do  not  affect
          	 active or already configured tuxTmachineTable instances. "
     ::= { tuxTdomain 12 }

tuxTdomainMaxGTT OBJECT-TYPE
     SYNTAX  INTEGER (0..32767)
     ACCESS  read-write
     STATUS  mandatory
     DESCRIPTION 
               " Default attribute setting for newly configured  instances
                 in the tuxTmachineTable group. 
                 Limitation: Changes to this  attribute  do  not  affect 
                 active or already configured tuxTmachineTable instances. "
     ::= { tuxTdomain 13 }

tuxTdomainMaxBufsType OBJECT-TYPE
     SYNTAX  INTEGER (1..32767)
     ACCESS  read-write
     STATUS  mandatory
     DESCRIPTION 
               " Maximum number of buffer subtypes that can be  accommo-
          	 dated in the bulletin board buffer subtype table. "
     ::= { tuxTdomain 14 }

tuxTdomainMaxBufType OBJECT-TYPE
     SYNTAX  INTEGER (1..32767)
     ACCESS  read-write
     STATUS  mandatory
     DESCRIPTION 
               " Maximum number of buffer types that can be accommodated
          	 in the bulletin board buffer type table. "
     ::= { tuxTdomain 15 }

tuxTdomainMaxDRT OBJECT-TYPE
     SYNTAX  INTEGER (0..32767)
     ACCESS  read-write
     STATUS  mandatory
     DESCRIPTION 
               " Maximum number of routing table  entries  that  can  be
          	 accommodated  in the bulletin board routing table.  One
          	 entry per tuxTroutingTable instance  is  required.   Addi-
          	 tional entries should be allocated to allow for runtime
          	 growth. "
     ::= { tuxTdomain 16 }

tuxTdomainMaxGroups OBJECT-TYPE
     SYNTAX  INTEGER (100..32767)
     ACCESS  read-write
     STATUS  mandatory
     DESCRIPTION 
               " Maximum number of server groups that  can  be  accommo-
          	 dated in the bulletin board server group table.
          	 Limitation: TUXEDO System/T Release 4.2.2  and  earlier
          	 sites  have  a fixed setting of 100 for this attribute.
          	 Interoperability with these sites requires that no more
          	 than  100  server  group entries be in use at any time.
          	 Release 4.2.2 and earlier sites will not be allowed  to
          	 join  an  application  that  has  more than 100 defined
          	 server  groups.   Additionally,  applications   already
          	 including  Release  4.2.2  or earlier sites will not be
          	 allowed to add server groups beyond 100. "
     ::= { tuxTdomain 17 }

tuxTdomainMaxMachines OBJECT-TYPE
     SYNTAX  INTEGER (256..8190)
     ACCESS  read-write
     STATUS  mandatory
     DESCRIPTION 
               " Maximum number of machines that can be accommodated  in
          	 the bulletin board machine table.
          	 Limitation: TUXEDO System/T Release 4.2.2 has  a  fixed
          	 setting  of  256 for this attribute.  Releases prior to
          	 Release 4.2.2 have a  fixed  setting  of  50  for  this
          	 attribute.   Interoperability  with  Release  4.2.2 and
          	 earlier sites requires that no  more  than  the  lowest
          	 fixed setting number of machine table entries be in use
          	 at any time.  Release 4.2.2 sites will not  be  allowed
          	 to  join  an application that has more than 256 defined
          	 machines.  Pre-Release 4.2.2 sites will not be  allowed
          	 to  join  an  application that has more than 50 defined
          	 machines.  Additionally, applications already including
          	 active  Release  4.2.2  or  earlier  sites  will not be
          	 allowed to add machines beyond  the  lowest  applicable
          	 limit. "
     ::= { tuxTdomain 18 }

tuxTdomainMaxQueues OBJECT-TYPE
     SYNTAX  INTEGER (1..8191)
     ACCESS  read-write
     STATUS  mandatory
     DESCRIPTION 
               "  Maximum number of queues to be accommodated in the bul-
          	  letin board queue table.
          	  Limitation: Release 4.2.2 and earlier sites may join an
          	  active application only if the setting for tuxTdomainMax-
		  Queues is equal to the setting for tuxTdomainMaxServers. "
     ::= { tuxTdomain 19 }

tuxTdomainMaxRFT OBJECT-TYPE
     SYNTAX  INTEGER (0..32767)
     ACCESS  read-write
     STATUS  mandatory
     DESCRIPTION 
               " Maximum number of routing criteria range table  entries
          	 to be accommodated in the bulletin board range criteria
          	 table.   One  entry  per  individual  range  within   a
          	 tuxTroutingRanges specification is required plus one 
		 additional entry per tuxTroutingTable class object.   
		 Additional  entries should be allocated to allow for 
		 runtime growth. "
     	 ::= { tuxTdomain 20 }

tuxTdomainMaxRTData OBJECT-TYPE
     SYNTAX  INTEGER (0..32760)
     ACCESS  read-write
     STATUS  mandatory
     DESCRIPTION 
               " Maximum string pool space to  be  accommodated  in  the
          	 bulletin  board string pool table.  Strings and carrays
          	 specified within tuxTroutingRanges values  are  stored  in  
		 the string  pool. Additional space should be allocated to
          	 allow for runtime growth. "
     ::= { tuxTdomain 21 }

tuxTdomainMaxServers OBJECT-TYPE
     SYNTAX  INTEGER (1..8191)
     ACCESS  read-write
     STATUS  mandatory
     DESCRIPTION 
               " Maximum number of servers to  be  accommodated  in  the
          	 bulletin board server table.  Allowances should be made
          	 in setting this attribute for system supplied  adminis-
          	 trative  servers.  Administration of each System/T site
          	 adds approximately one server.  Additionally,  if  TMSs
          	 are  specified  for  any  server  groups (see  
		 tuxTgroupTmsName ), then they will be  booted  along
          	 with  their server group and should be accounted for in
          	 setting tuxTdomainMaxServers. "
     ::= { tuxTdomain 22 }

tuxTdomainMaxServices OBJECT-TYPE
     SYNTAX  INTEGER (1..32767)
     ACCESS  read-write
     STATUS  mandatory
     DESCRIPTION 
               " Maximum number of services to be  accommodated  in  the
          	 bulletin  board  service  table.   Allowances should be
          	 made in setting  this  attribute  for  system  supplied
          	 servers  offering services for administrative purposes.
          	 Administration of each System/T site adds approximately
          	 five services.  Other administrative components such as
          	 /WS, /Q, and /DM may also add  administrative  services
          	 that should be accounted for. "
     ::= { tuxTdomain 23 }

tuxTdomainMaxACLgroups OBJECT-TYPE
     SYNTAX  INTEGER (1..16384)
     ACCESS  read-write
     STATUS  mandatory
     DESCRIPTION 
               " Maximum number of group identifiers that  can  be  used
          	 for  ACL permissions checking.  The maximum group iden-
          	 tifier that can be defined is tuxTdomainMaxACLGroups - 1. "
     ::= { tuxTdomain 24 }

tuxTdomainCMTRET OBJECT-TYPE
     SYNTAX  INTEGER {
			complete(1),
			logged(2)
		}
     ACCESS  read-write
     STATUS  mandatory
     DESCRIPTION 
               " Initial setting of the TP_COMMIT_CONTROL characteristic
          	 for  all  client  and  server  processes  in a System/T
          	 application.  logged(1) initializes the  TP_COMMIT_CONTROL
          	 characteristic  to TP_CMT_LOGGED; otherwise, it is ini-
          	 tialized to TP_CMT_COMPLETE.  See  the  description  of
          	 the System/T ATMI function tpscmt(3) for details on the
          	 setting of this characteristic.
          	 Limitation: Runtime modifications to this attribute  do
          	 not affect active clients and servers. "
     ::= { tuxTdomain 25 }

tuxTdomainLoadBalance OBJECT-TYPE
     SYNTAX  INTEGER {
			yes(1),
			no(2)
		}
     ACCESS  read-write
     STATUS  mandatory
     DESCRIPTION 
               " Load balancing is/will be on yes(1) or off no(2).
          	 Limitation: Runtime modifications to this attribute  do
          	 not affect active clients and servers. "
     ::= { tuxTdomain 26 }

tuxTdomainNotify OBJECT-TYPE 
     SYNTAX  INTEGER {
			dipin(1),
			signal(2),
			ignore(3)
		}
     ACCESS  read-write
     STATUS  mandatory
     DESCRIPTION 
               " Default notification detection method to be used by the
          system   for   unsolicited   messages  sent  to  client
          processes.  This default value can be overridden  on  a
          per-client  basis  using the appropriate tpinit(3) flag
          value.   Note  that  once  unsolicited   messages   are
          detected,  they  are  made available to the application
          through the  application  defined  unsolicited  message
          handling routine identified via the tpsetunsol(3) func-
          tion.

          The value dipin(1) specifies that  dip-in-based  notifica-
          tion  detection  should  be  used.  This means that the
          system will only detect notification messages on behalf
          of a client process while within ATMI calls.  The point
          of detection within any particular  ATMI  call  is  not
          defined  by  the  system, and dip-in detection will not
          interrupt blocking system calls.  dipin(1) is the default
          notification detection method.
          The value signal(2) specifies that signal-based  notifica-
          tion  detection  should  be  used.  This means that the
          system sends a signal  to  the  target  client  process
          after the notification message has been made available.
          The system installs a signal catching routine on behalf
          of clients selecting this method of notification.

          The value ignore(3) specifies that by  default,  notifica-
          tion messages are to be ignored by application clients.
          This would be appropriate in  applications  where  only
          clients  that  request  notification  at tpinit(3) time
          should receive unsolicited messages.
          Limitations: Runtime modifications to this attribute do
          not  affect  active  clients.   All signaling of client
          processes is done by  administrative  system  processes
          and  not  by  application  processes.   Therefore, only
          clients running with the same UNIX System user identif-
          ier can be notified using the signal(2) method. "
     ::= { tuxTdomain 27 }

tuxTdomainSystemAccess OBJECT-TYPE 
     SYNTAX  INTEGER {
			fastpath(1),
			protected(2),
			fastpath-no-override(3),
			protected-no-override(4)
		}
     ACCESS  read-write
     STATUS  mandatory
     DESCRIPTION 
               " Default mode used by System/T libraries within applica-
          	 tion  processes  to  gain access to System/T's internal
          	 tables.  fastpath(1) specifies  that  System/T's  internal
          	 tables  are accessible by System/T libraries via unpro-
          	 tected shared memory for fast access.  protected(2) speci-
          	 fies  that System/T's internal tables are accessible by
          	 System/T libraries  via  protected  shared  memory  for
          	 safety   against   corruption   by   application  code.
          	 No_override can be specified to indicate that the  mode
          	 selected cannot be overridden by an application process
          	 using flags available for use with tpinit(3).
          	 Limitations: Updates to this attribute value in a  run-
          	 ning  application affect only newly started clients and
          	 newly configured tuxTsrvrTbl objects. " 
     ::= { tuxTdomain 28 }

tuxTdomainOptions OBJECT-TYPE 
    SYNTAX  INTEGER {
			lan(1),
			migrate(2),
			accstats(3),
			lan-migrate(4),
			lan-accstats(5),
			migrate-accstats(6),
			lan-migrate-accstats(7),
			none(8)
		}
     ACCESS  read-write
     STATUS  mandatory
     DESCRIPTION 
               " Combination of application options in  effect.
          	 The following options can be specified in the combinations
		 listed above:
          	 Lan - Networked application.
          	 Migrate - Allow server group migration.
          	 Accstats - Exact statistics (SHM mode only).
          	 Limitation: Only the Accstats may be set or reset in an
          	 active application. "
     ::= { tuxTdomain 29 }

tuxTdomainSignal OBJECT-TYPE 
     SYNTAX  INTEGER {
			sigusr1(1),
			sigusr2(2)
		}
     ACCESS  read-write
     STATUS  mandatory
     DESCRIPTION 
               " Signal to be used for  signal-based  notification  (see
          	 tuxTdomainNotify above). "
     ::= { tuxTdomain 30 }

tuxTdomainSecurity OBJECT-TYPE 
     SYNTAX  DisplayString
     ACCESS  read-write
     STATUS  mandatory
     DESCRIPTION
               " Format:
                                <security_mode>[/<app_passwd>]

                 where <security_mode> can have following values:

                                none,
                                app-pw,
                                USER_AUTH,
                                ACL, or
                                MANDATORY_ACL.

                 <app_passwd> is needed whenever the <security_mode> is being
                 set to anything but `none' (unless it is allready defined).

                 To change the value of the <app_passwd> SET this object to:

                                 <current_security_mode>/<new_passwd>          

                 On a GET operation this object only returns the security
                 mode and the password is not returned.

                 This object represents the type of application security.
                 A  string  value `none' for this attribute indicates that
                 security is/will be turned off.
                 The value `app-pw/<app_passwd>' indicates that
                 application password security is to be enforced (clients
                 must provide the application  password during initiali-
                 zation).
                 The value `USER_AUTH' is similar to `app-pw' but, in
                 addition, indicates that per-user authentication will be
                 done during client initialization.  The value `ACL' is
                 similar to `USER_AUTH' but, in addition, indicates that
                 access control checks will be done on service names, queue
                 names, and event names.  If an associated ACL is not
                 found for a name, it is assumed that permission is granted.
                 The value `MANDATORY_ACL' is similar to `ACL'  but
                 permission  is denied if an associated ACL is not found for
                 the name."                                                    
     ::= { tuxTdomain 31 }

-- This object has been merged with tuxTdomainSecurity above.
--tuxTdomainPassword OBJECT-TYPE 
--   SYNTAX  DisplayString (SIZE (0..8)) 
--   ACCESS  read-write		
--   STATUS  mandatory
--   DESCRIPTION 
--             " Clear text application  password.   This  attribute  is
--        	 ignored if the tuxTdomainSecurity attribute is set to nothing.
--        	 Note that the system will  automatically  encrypt  this
--        	 information on behalf of the administrator. "
--   ::= { tuxTdomain 32 }

tuxTdomainAuthsvc OBJECT-TYPE 
     SYNTAX  DisplayString (SIZE (1..15)) 
     ACCESS  read-write
     STATUS  mandatory
     DESCRIPTION 
               " Application authentication service invoked by the  sys-
          	 tem for each client joining the system.  This attribute
          	 is ignored if the tuxTdomainSecurity attribute is set to 
		 none(1) or to app-pw(2). "
     ::= { tuxTdomain 33 }

tuxTdomainScanUnit OBJECT-TYPE 
     SYNTAX  INTEGER (0..60) 
     ACCESS  read-write
     STATUS  mandatory
     DESCRIPTION 
               " Interval of time (in seconds) between periodic scans by
          	 the  system.   Periodic  scans  are  used to detect old
          	 transactions  and  timed-out  blocking   calls   within
          	 service   requests.    The  tuxTdomainBBLQuery, 
		 tuxTdomainBlockTime, tuxTdomainDBBLWait, and tuxTdomain-
		 SanityScan  objects  are  multipliers  of  this  value.  
		 Passing a value of 0 for this attribute on a SET operation 
		 will cause  the  attribute to be reset to its default value. "
     ::= { tuxTdomain 34 }

tuxTdomainBBLQuery OBJECT-TYPE 
     SYNTAX  INTEGER (0..32767) 
     ACCESS  read-write
     STATUS  mandatory
     DESCRIPTION 
               " Multiplier of the tuxTdomainScanUnit object indicating time
          	 between  DBBL  status  checks  on registered BBLs.  The
          	 DBBL checks to ensure that all BBLs  have  reported  in
          	 within  the  tuxTdomainBBLQuery  cycle.  If a BBL has not been
          	 heard from, the DBBL sends a message to that BBL asking
          	 for status.  If no reply is received, the BBL is parti-
          	 tioned.  Passing a value of 0 for this attribute  on  a
          	 SET  operation  will cause the attribute to be reset to
          	 its default value.  This attribute value should be  set
          	 to  at  least twice the value set for tuxTdomainSanityScan "
     ::= { tuxTdomain 35 }

tuxTdomainBlockTime OBJECT-TYPE 
     SYNTAX  INTEGER (0..32767) 
     ACCESS  read-write
     STATUS  mandatory
     DESCRIPTION 
               " Multiplier of the tuxTdomainScanUnit object indicating  the
          	 minimum  amount of time a blocking ATMI call will block
          	 before timing out.  Passing  a  value  of  0  for  this
          	 attribute  on  a SET operation will cause the attribute
          	 to be reset to its default value. "
     ::= { tuxTdomain 36 }

tuxTdomainDBBLWait OBJECT-TYPE 
     SYNTAX  INTEGER (0..32767) 
     ACCESS  read-write
     STATUS  mandatory
     DESCRIPTION 
               " Multiplier of the tuxTdomainScanUnit object indicating max-
          	 imum amount of time a DBBL should wait for replies from
          	 its BBLs before timing out.  Passing a value of  0  for
          	 this attribute on a SET operation will cause the attri-
          	 bute to be reset to its default value. "
     ::= { tuxTdomain 37 }

tuxTdomainSanityScan OBJECT-TYPE 
     SYNTAX  INTEGER (0..32767) 
     ACCESS  read-write
     STATUS  mandatory
     DESCRIPTION 
               " Multiplier of the tuxTdomainScanUnit object indicating time
          	 between  basic  sanity  checks  of  the system.  Sanity
          	 checking includes client/server viability  checks  done
          	 by  each  BBL  for clients/servers running on the local
          	 machine as well as BBL status check-ins (MP mode only).
          	 Passing a value of 0 for this attribute on a SET opera-
          	 tion will cause  the  attribute  to  be  reset  to  its
          	 default value. "
     ::= { tuxTdomain 38 }

tuxTdomainCurDRT OBJECT-TYPE 
     SYNTAX  INTEGER (0..32767) 
     ACCESS  read-only
     STATUS  mandatory
     DESCRIPTION 
               " Current number of in use bulletin board  routing  table
          	 entries. "
     ::= { tuxTdomain 39 }

tuxTdomainCurGroups OBJECT-TYPE 
     SYNTAX  INTEGER (0..32767) 
     ACCESS  read-only
     STATUS  mandatory
     DESCRIPTION 
               "  Current number of in use bulletin  board  server  group
          	  table entries. "
     ::= { tuxTdomain 40 }

tuxTdomainCurMachines OBJECT-TYPE 
     SYNTAX  INTEGER (0..32767) 
     ACCESS  read-only
     STATUS  mandatory
     DESCRIPTION 
               " Current number of configured machines. "
     ::= { tuxTdomain 41 }

tuxTdomainCurQueues OBJECT-TYPE 
     SYNTAX  INTEGER (0..32767) 
     ACCESS  read-only
     STATUS  mandatory
     DESCRIPTION 
               " Current number of in use  bulletin  board  queue  table
          	 entries. "
     ::= { tuxTdomain 42 }

tuxTdomainCurRFT OBJECT-TYPE 
     SYNTAX  INTEGER (0..32767) 
     ACCESS  read-only
     STATUS  mandatory
     DESCRIPTION 
               " Current number of in use bulletin  board  routing  cri-
          	 teria range table entries. "
     ::= { tuxTdomain 43 }

tuxTdomainCurRTdata OBJECT-TYPE 
     SYNTAX  INTEGER (0..32767) 
     ACCESS  read-only
     STATUS  mandatory
     DESCRIPTION 
               " Current size of routing table string pool. "
     ::= { tuxTdomain 44 }

tuxTdomainCurServers OBJECT-TYPE 
     SYNTAX  INTEGER (0..32767) 
     ACCESS  read-only
     STATUS  mandatory
     DESCRIPTION 
               " Current number of in use bulletin  board  server  table
          	 entries. "
     ::= { tuxTdomain 45 }

tuxTdomainCurServices OBJECT-TYPE 
     SYNTAX  INTEGER (0..32767) 
     ACCESS  read-only
     STATUS  mandatory
     DESCRIPTION 
               " Current number of in use bulletin board  service  table
          	 entries. "
     ::= { tuxTdomain 46 }

tuxTdomainCursType OBJECT-TYPE 
     SYNTAX  INTEGER (0..32767) 
     ACCESS  read-only
     STATUS  mandatory
     DESCRIPTION 
               " Current number of in use bulletin board  subtype  table
          	 entries. "
     ::= { tuxTdomain 47 }

tuxTdomainCurType OBJECT-TYPE 
     SYNTAX  INTEGER (0..32767) 
     ACCESS  read-only
     STATUS  mandatory
     DESCRIPTION 
               " Current number of in  use  bulletin  board  type  table
          	 entries. "
     ::= { tuxTdomain 48 }

tuxTdomainHwDRT OBJECT-TYPE 
     SYNTAX  INTEGER (0..32767) 
     ACCESS  read-only
     STATUS  mandatory
     DESCRIPTION 
               " High water number of  in  use  bulletin  board  routing
          	 table entries. "
     ::= { tuxTdomain 49 }

tuxTdomainHwGroups OBJECT-TYPE 
     SYNTAX  INTEGER (0..32767) 
     ACCESS  read-only
     STATUS  mandatory
     DESCRIPTION 
               " High water number of in use bulletin board server group
          	 table entries. "
     ::= { tuxTdomain 50 }

tuxTdomainHwMachines OBJECT-TYPE 
     SYNTAX  INTEGER (0..32767) 
     ACCESS  read-only
     STATUS  mandatory
     DESCRIPTION 
               " High water number of configured machines. "
     ::= { tuxTdomain 51 }

tuxTdomainHwQueues OBJECT-TYPE 
     SYNTAX  INTEGER (0..32767) 
     ACCESS  read-only
     STATUS  mandatory
     DESCRIPTION 
               " High water number of in use bulletin board queue  table
          	 entries. "
     ::= { tuxTdomain 52 }

tuxTdomainHwRFT OBJECT-TYPE 
     SYNTAX  INTEGER (0..32767) 
     ACCESS  read-only
     STATUS  mandatory
     DESCRIPTION 
               " High water number of in use bulletin board routing cri-
          	 teria range table entries. "
     ::= { tuxTdomain 53 }

tuxTdomainHwRTdata OBJECT-TYPE 
     SYNTAX  INTEGER (0..32767) 
     ACCESS  read-only
     STATUS  mandatory
     DESCRIPTION 
               " High water size of routing table string pool. "
     ::= { tuxTdomain 54 }

tuxTdomainHwServers OBJECT-TYPE 
     SYNTAX  INTEGER (0..32767) 
     ACCESS  read-only
     STATUS  mandatory
     DESCRIPTION 
               " High water number of in use bulletin board server table
          	 entries. "
     ::= { tuxTdomain 55 }

tuxTdomainHwServices OBJECT-TYPE 
     SYNTAX  INTEGER (0..32767) 
     ACCESS  read-only
     STATUS  mandatory
     DESCRIPTION 
               " High water number of  in  use  bulletin  board  service
          	 table entries. "
     ::= { tuxTdomain 56 }

tuxTdomainMaxNetGroups OBJECT-TYPE 
     SYNTAX  INTEGER (1..8191) 
     ACCESS  read-write
     STATUS  mandatory
     DESCRIPTION 
               " This represents the maximum number of groups that can be 
          	 configured.
		 SUPPORT: Tuxedo 6.4 and later versions only. "
     ::= { tuxTdomain 58 }

-- Added : BEGIN-JANUS-NS-TUXEDO7.1-041400

tuxTdomainSignatureAhead OBJECT-TYPE 
     SYNTAX  INTEGER (1..2147483647)
     ACCESS  read-write
     STATUS  mandatory
     DESCRIPTION 
	"Number of seconds into the future a valid signature's timestamp may be,
     when compared to the local machine's clock.
		 SUPPORT: Tuxedo 7.1 and later versions only. "
     ::= { tuxTdomain 70 }

tuxTdomainSignatureBehind OBJECT-TYPE 
     SYNTAX  INTEGER (1..2147483647)
     ACCESS  read-write
     STATUS  mandatory
     DESCRIPTION 
	"Number of seconds into the past a valid signature's timestamp may be,
     when compared to the local machine's clock.
		 SUPPORT: Tuxedo 7.1 and later versions only. "
     ::= { tuxTdomain 80 }

tuxTdomainEncryptionRequired OBJECT-TYPE 
     SYNTAX  INTEGER {
		yes(1),
		no(2)
	}
     ACCESS  read-write
     STATUS  mandatory
     DESCRIPTION 
	 "If set to yes every application service in this domain requires an
     encrypted input message buffer.
		 SUPPORT: Tuxedo 7.1 and later versions only. "
     ::= { tuxTdomain 90 }

tuxTdomainSignatureRequired OBJECT-TYPE 
     SYNTAX  INTEGER {
		yes(1),
		no(2)
	}
     ACCESS  read-write
     STATUS  mandatory
     DESCRIPTION 
	 "If set to yes every application service in this domain requires a valid
     digital signature on its input message buffer.
		 SUPPORT: Tuxedo 7.1 and later versions only. "
     ::= { tuxTdomain 100 }

-- Added : END-JANUS-NS-TUXEDO7.1-041400

-- tuxTdomainList table which was {tuxTdomain 57}, was made obsolete 
--   Manager 2.0 onwards 

tuxMaxObjects OBJECT-TYPE
     SYNTAX  INTEGER
     ACCESS  read-write
     STATUS  mandatory
     DESCRIPTION
               " The default maximum number of active objects to be accommodated
                 in the Active Object Map tables in the CORBA C++ Interface 
				 bulletin board.

                 SUPPORT: CORBA C++ Interface only."
     ::= { tuxTdomain 63 }
 
-- Added : END-JANUS-NS-TUXEDO7.1-041400

tuxMaxInterfaces OBJECT-TYPE
     SYNTAX  INTEGER (1..32765)
     ACCESS  read-write
     STATUS  mandatory
     DESCRIPTION
               " Specifies the maximum number of interfaces to be accommodated
                 in the interface table of the bulletin board. If not specified,
                 the default is 100.
 
                 NOTE: All instances of an interface occupy and reuse the same
                 slot in the interface table in the bulletin board. For example,
                 if server SVR1 advertises interfaces IF1 and IF2, SVR2 advert-
                 ises IF2 and IF3, and SVR3 advertises IF3 and IF4, the
                 interface count is 4 (not 6) when calculating tuxMaxInterfaces.
 
                 SUPPORT: CORBA  C++ Interface only. "
     ::= { tuxTdomain 68 }
 
tuxCurInterfaces OBJECT-TYPE
     SYNTAX  INTEGER
     ACCESS  read-only
     STATUS  mandatory
     DESCRIPTION
               " The current number of interface entries used in the bulletin
                 board interface tables.

                 SUPPORT: CORBA C++ Interface only."
     ::= { tuxTdomain 73 }

tuxHwInterfaces OBJECT-TYPE
     SYNTAX  INTEGER
     ACCESS  read-only
     STATUS  mandatory
     DESCRIPTION
               " The high water number of interface entries used in the bulletin
                 board interface tables.

                 SUPPORT: CORBA C++ Interface only. "
     ::= { tuxTdomain 78 }

--- **************************************************************************
--- tuxTgroupTable group
--- This group represents application attributes pertaining  to  a  particular 
--- server group.  These attribute values represent group identification, 
--- location, and DTP information.
--- **************************************************************************

tuxTgroupTable OBJECT-TYPE
     SYNTAX  SEQUENCE OF TuxTgroupEntry
     ACCESS   not-accessible
     STATUS  mandatory
     DESCRIPTION 
               "Table representing the set of attributes for various server
		groups "
     ::= { tuxTgroup 1 }

tuxTgroupEntry OBJECT-TYPE
     SYNTAX  TuxTgroupEntry
     ACCESS  not-accessible 
     STATUS  mandatory
     DESCRIPTION 
               "A row of attributes in the tuxTgroupTable. (corresponding to 
		one server group
		Creation of a new group ( instance ):
		===================================
		A set request for a non-existing instance with atleast tuxT-
		groupName and tuxTgroupLMID is required. "
     INDEX { tuxTgroupNo }
     ::= { tuxTgroupTable 1 }

TuxTgroupEntry ::= SEQUENCE {
     tuxTgroupName
       DisplayString,
     tuxTgroupNo
        INTEGER,
     tuxTgroupLMID
        DisplayString,
     tuxTgroupState
        INTEGER,
     tuxTgroupCurLMID
        DisplayString,
     tuxTgroupCloseInfo
        DisplayString,
     tuxTgroupOpenInfo
   	DisplayString,
     tuxTgroupTMScount
	INTEGER,
     tuxTgroupTMSname
	DisplayString,
     tuxTgroupEncryptionRequired
	INTEGER,
     tuxTgroupSignatureRequired
	INTEGER
     }   

tuxTgroupName   OBJECT-TYPE
     SYNTAX  DisplayString (SIZE (1..30))
     ACCESS  read-write		-- writable only during row creation
     STATUS  mandatory
     DESCRIPTION
               " Logical name of the server group.  The group name  must
          	 be  unique  within all group names in the tuxTgroupTable
          	 and tuxTgroupLMID values  in  the  tuxTmachineTable  class.
		 Server group  names  cannot contain an asterisk `*', comma,
		 or colon. 
		Note: This object can be set only during row creation."
     ::=  { tuxTgroupEntry 1 }

tuxTgroupNo   OBJECT-TYPE
     SYNTAX  INTEGER (1..29999)
     ACCESS  read-write		-- writable only during row creation
     STATUS  mandatory
     DESCRIPTION 
               " Group number associated with this server group. 
		Note: This object can be set only during row creation."
     ::=  { tuxTgroupEntry 2 }

tuxTgroupLMID   OBJECT-TYPE
     SYNTAX  DisplayString (SIZE (1..61))
     ACCESS  read-write
     STATUS  mandatory
     DESCRIPTION 
               " Primary machine logical  machine  identifier  for  this
          	 server  group  (LMID1)  and  optional secondary logical
          	 machine identifier (LMID2).  The secondary  LMID  indi-
          	 cates  the  machine  to  which  the server group can be
          	 migrated (if the MIGRATE option  is  specified  in  the
          	 tuxTdomainOptions  attribute).   A single LMID speci-
          	 fied on a GET operation will match either  the  primary
          	 or secondary LMID.  Note that the location of an active
          	 group is available in the tuxTgroupCurLMID object. Logi-
          	 cal  machine  identifiers  specified  with  the 
		 tuxTgroupLMID object must be already configured.
          	 Limitation: Modifications  to  this  attribute  for  an
          	 active  object may only change the backup LMID designa-
          	 tion for the group. Format: LMID1[,LMID2]"
     ::=  { tuxTgroupEntry 3 }

tuxTgroupState   OBJECT-TYPE
     SYNTAX  INTEGER {
			active(1),
			inactive(2),
			migrating(3),
			invalid(4),
			re-activate(5),
			suspend-services(6),
			resume-services(7)
		}
     ACCESS  read-write
     STATUS  mandatory
     DESCRIPTION
               " A GET operation will  retrieve  configuration  and
               runtime   information  for  the  selected  tuxTgroupTable
               instance(s).   The  following  states  indicate  the
               meaning  of a tuxTgroupState returned in response to a
               GET  request.   States  not  listed  will  not  be
               returned.

               active(1)    tuxTgroupTable  defined  and  active
                            (TMS   and/or  application  servers).
                            Server  groups  with   non   0-length
                            values  for  the tuxTgroupTmsName object
                            are considered  active  if  the  TMSs
                            associated with the group are active.
                            Otherwise,  a  group  is   considered
                            active  if any server in the group is

               inactive(2)  tuxTgroupTable object defined and inactive.

               migrating(3) tuxTgroupTable object defined and  currently
                            in a state of migration to the secon-
                            dary logical machine.  The  secondary
                            logical  machine is the one listed in
                            tuxTgroupLmid   that   does    not    match
                            tuxTgroupCurLMID.

          SET: 
               A SET operation will update configuration and run-
               time  information for the selected tuxTgroupTable instance.
               The following states indicate  the  meaning  of  a
               tuxTgroupState  set in a SET request.  States not listed
               may not be set.

               invalid(4)   Delete tuxTgroupTable  instance  for  applica-
                            tion.  State change allowed only when
                            in the  inactive(2)  state.   Successful
                            return   leaves  the  object  in  the
                            invalid(4) state.
               active(1)    Activate the tuxTgroupTable  instance.   
			    State change allowed only when in the 
			    inactive(2) or migrating(3)  state.   
                            If the  group  is  currently  in  the
                            inactive(2) state, then TMS and applica-
                            tion servers are started on the primary 
			    logical  machine  if  the
                            primary  logical  machine  is active;
                            otherwise, the  TMS  and  application
                            servers  are started on the secondary
                            logical machine if it is active.   If
                            neither  machine  is active, then the
                            request fails.

                            If the  group  is  currently  in  the
                            migrating(3) state,  then  the  active
                            secondary logical machine (identified
                            as the alternate to tuxTgroupCurLMID in 
			    the tuxTgroupLmid list) is used  to  start  
			    TMS and  application  servers  if  it  is
                            active.    Otherwise,   the   request
                            fails.
                            Successful return leaves  the  object
                            in the ACTive state.

               re-activate(5)
			    Identical  to  a  transition  to  the
                            active(1)  state  except that this state
                            change is also allowed in the  active(1)
                            state in addition to being allowed in
                            the inactive(2) and migrating(3) states.

               inactive(2)  Deactivate the tuxTgroupTable instance.   
			    TMS and  application  servers are
                            deactivated.   State  change  allowed
                            only when in the active(1) or migrating(3)
                            state.   Successful return leaves the
                            object in the inactive(2) state.

               migrating(3) Deactivate the tuxTgroupTable instance on  
			    its active primary logical machine
                            (tuxTgroupCurLMID) and prepare the group to
                            be  migrated to the secondary logical
                            machine.  State change  allowed  only
                            when in the active(1) state.  Successful
                            return  leaves  the  object  in   the
                            migrating(3) state.
	suspend-services(6) Suspend the application services in the group.
			    A SET operation to this state is allowed only
			    when the group is in active(1) state. The oper-
			    ation leaves the group in active(1) state but
			    with all its application services in a suspend-
			    ed state.
			    SUPPORT: This is only available in TUXEDO 6.4 and
				  later releases.
	resume-services(7) Unsuspend/resume all application services in the
			   group, which are marked as suspended. This operation
			   is allowed only when the group is in active(1)
			   state. The operation leaves the group in active(1)
			   state.
			   Limitation: The operation will fail in a mixed rele-
			   ase application where any pre-release 6.4 machine
			   is active. "
     ::=  { tuxTgroupEntry 4 }

tuxTgroupCurLMID   OBJECT-TYPE
     SYNTAX  DisplayString (SIZE (1..30))
     ACCESS  read-only
     STATUS  mandatory
     DESCRIPTION 
               " Current logical machine on which the  server  group  is
          	 running.   This  attribute  will  not  be  returned for
          	 server groups that are not active. "
     ::=  { tuxTgroupEntry 5 }

tuxTgroupCloseInfo   OBJECT-TYPE
     SYNTAX  DisplayString (SIZE (0..256))
     ACCESS  read-write
     STATUS  mandatory
     DESCRIPTION 
               " If a non 0-length value other than `TMS'  is  specified
          	 for the tuxTgroupTMSname object, then this object value
          	 indicates the resource  manager  dependent  information
          	 needed when terminating access to the resource manager.
          	 Otherwise, this attribute value is ignored.
	 
          	 The format for this object value is dependent on the
          	 requirements  of  the  vendor  providing the underlying
          	 resource manager.  The information required by the ven-
          	 dor  must  be  prefixed with ``rm_name:'', which is the
          	 published name of the vendor's transaction (XA)  inter-
          	 face followed immediately by a colon (:).
          	 A 0-length string value for this attribute  means  that
          	 the resource manager for this group (if specified) does
          	 not require any  application  specific  information  to
          	 close access to the resource.
          	 Limitation: Runtime  modifications  to  this  attribute
          	 will not affect active servers in the group. "
     ::=  { tuxTgroupEntry 6 }

tuxTgroupOpenInfo   OBJECT-TYPE
     SYNTAX  DisplayString (SIZE (0..256))
     ACCESS  read-write
     STATUS  mandatory
     DESCRIPTION 
               " If a non 0-length value other than `TMS'  is  specified
          	 for the tuxTgroupTMSname object, then this object value
          	 indicates the resource  manager  dependent  information
          	 needed  when initiating access to the resource manager.
          	 Otherwise, this object value is ignored.
          	 The format for this object value is dependent on the
          	 requirements  of  the  vendor  providing the underlying
          	 resource manager.  The information required by the ven-
          	 dor  must  be  prefixed with ``rm_name:'', which is the
          	 published name of the vendor's transaction (XA)  inter-
          	 face followed immediately by a colon (:).
          	 A 0-length string value for this attribute  means  that
          	 the resource manager for this group (if specified) does
          	 not require any  application  specific  information  to
          	 open access to the resource.
          	 Limitation: Runtime  modifications  to  this  attribute
          	 will not affect active servers in the group. "
     ::=  { tuxTgroupEntry 7 }

tuxTgroupTMScount   OBJECT-TYPE
     SYNTAX  INTEGER (0..11)
     ACCESS  read-write
     STATUS  mandatory
     DESCRIPTION 
               " If a non 0-length value is specified for the tuxTgroupTMSname
          	 object,  then  this  object  value  indicates the
          	 number of transaction manager servers to start for  the
          	 associated  group.   Otherwise, this object value is
          	 ignored. "
     ::=  { tuxTgroupEntry 8 }

tuxTgroupTMSname   OBJECT-TYPE
     SYNTAX  DisplayString (SIZE (0..256))
     ACCESS  read-write
     STATUS  mandatory
     DESCRIPTION 
               " Transaction manager server a.out associated  with  this
          	 group.   This parameter must be specified for any group
          	 entry whose servers  will  participate  in  distributed
          	 transactions  (transactions  across  multiple  resource
          	 managers and possibly machines that  are  started  with
          	 tpbegin(3), and ended with tpcommit(3)/tpabort(3)).
          	 The value `TMS' is reserved to indicate use of the null
          	 XA interface.  If a non-empty value other than `TMS' is
          	 specified, then a tuxTmachineTlogDevice must be specified 
		 for  the
          	 machine(s)  associated  with  the primary and secondary
          	 logical machines for this object.
          	 A unique server identifier  is  selected  automatically
          	 for each TM server, and the servers will be restartable
          	 an unlimited number of times. "
     ::=  { tuxTgroupEntry 9 }

-- Added : BEGIN-JANUS-NS-TUXEDO7.1-041400

tuxTgroupEncryptionRequired   OBJECT-TYPE
     SYNTAX  INTEGER {
		yes(1),
		no(2)
	}
     ACCESS  read-write
     STATUS  mandatory
     DESCRIPTION 
	    "If set to yes every application service in this group requires an
     encrypted input message buffer. 
		Support: Tuxedo 7.1 and later"
     ::=  { tuxTgroupEntry 20 }


tuxTgroupSignatureRequired   OBJECT-TYPE
     SYNTAX  INTEGER {
		yes(1),
		no(2)
	}
     ACCESS  read-write
     STATUS  mandatory
     DESCRIPTION 
	"If set to yes every application service in this group requires a valid
     digital signature on its input message buffer.
		Support: Tuxedo 7.1 and later"
     ::=  { tuxTgroupEntry 30 }

-- Added : END-JANUS-NS-TUXEDO7.1-041400

--- ************************************************************************
---  tuxTmachine Group
---  The tuxTmachineTable group represents application  attributes  per-
---  taining  to  a  particular  machine.  These attribute values
---  represent  machine  characteristics,   per-machine   sizing,
---  statistics,   customization   options,   and   UNIX   System
---  filenames.
---  This group is availabe for configured-inactive as well as configured
---  -active machines in the application. 
--- ************************************************************************

tuxTmachineTable OBJECT-TYPE
     SYNTAX  SEQUENCE OF TuxTmachineEntry
     ACCESS   not-accessible
     STATUS  mandatory
     DESCRIPTION
               "Global Table for application attributes pertaining to parti-
		cular machines. A row in this table along with the objects in
		tuxTmachineActive group constitutes the complete set of 
		attributes for a particular machine. " 
     ::= { tuxTmachine 1 }

tuxTmachineEntry OBJECT-TYPE
     SYNTAX  TuxTmachineEntry
     ACCESS  not-accessible 
     STATUS  mandatory
     DESCRIPTION
               "One row of attributes in the tuxTmachineTable table.
		Creation of a new group ( instance ):
		===================================
		A set request for a non-existing instance with atleast tuxT-
		machineLmid, tuxTmachineTuxDir, tuxTmachineTuxConfig and 
		tuxTmachineAppDir is required. For a multi machine TUXEDO 
		application tuxTmachineNaddr , tuxTmachineNlsAddr and 
		tuxTmachineBridge are also needed. "
     INDEX { tuxTmachinePmid }
     ::= { tuxTmachineTable 1 }

TuxTmachineEntry ::= SEQUENCE {
     tuxTmachinePmid
       DisplayString,
     tuxTmachineLmid
        DisplayString,
     tuxTmachineTuxConfig
        DisplayString,
     tuxTmachineTuxDir
        DisplayString,
     tuxTmachineAppDir
        DisplayString,
     tuxTmachineState
	INTEGER,
     tuxTmachineUid
	INTEGER,
     tuxTmachineGid
	INTEGER,
     tuxTmachineEnvFile
	DisplayString,
     tuxTmachinePerm
	DisplayString,
     tuxTmachineUlogPfx
	DisplayString,
     tuxTmachineType
	DisplayString,
     tuxTmachineMaxAccessers
	INTEGER,
     tuxTmachineMaxConv
	INTEGER,
     tuxTmachineMaxGtt
	INTEGER,
     tuxTmachineMaxWsClients
	INTEGER,
     tuxTmachineMaxAclCache
	INTEGER,
     tuxTmachineTlogDevice
	DisplayString,
     tuxTmachineTlogName
	DisplayString,
     tuxTmachineTlogSize
	INTEGER,
     tuxTmachineBridge
	DisplayString,
     tuxTmachineNaddr
	DisplayString,
     tuxTmachineNlsaddr
	DisplayString,
     tuxTmachineCmpLimit
	DisplayString,
     tuxTmachineTmNetLoad
	INTEGER,
     tuxTmachineSpinCount
	INTEGER,
     tuxTmachineRole
	INTEGER,
     tuxTmachineMinor
	INTEGER,
     tuxTmachineRelease
	INTEGER,
     tuxTmachineMaxPendingBytes
	INTEGER,
     tuxMachineMaxObjects
	INTEGER,
     tuxTmachineEncryptionRequired
	INTEGER,
     tuxTmachineSignatureRequired
	INTEGER
     }

tuxTmachinePmid   OBJECT-TYPE
     SYNTAX  DisplayString (SIZE (1..30))
     ACCESS  read-write		-- writable only during row creation
     STATUS  mandatory
     DESCRIPTION 
               " Physical machine identifier.  For UNIX systems this should 
          	 match  the  nodename  as  returned by the `uname -n' command 
		 when run on the identified system. In Windows NT it should
		 match the computer name and the name configured with the name
		 server. 
		Note: This object can be set only during row creation."
     ::=  { tuxTmachineEntry 1 }

tuxTmachineLmid   OBJECT-TYPE
     SYNTAX  DisplayString (SIZE (1..30))
     ACCESS  read-write		-- writable only during row creation
     STATUS  mandatory
     DESCRIPTION 
               " Logical machine identifier.  
		 Note: This object can be updated only during row creation."
     ::=  { tuxTmachineEntry 2 }

tuxTmachineTuxConfig   OBJECT-TYPE
     SYNTAX  DisplayString (SIZE (2..256))
     ACCESS  read-write
     STATUS  mandatory
     DESCRIPTION 
               " Absolute pathname of  the  file  or  device  where  the
          	 binary  TUXEDO  System/T configuration file is found on
          	 this machine.  The administrator need only maintain one
          	 such   file,   namely   the   one   identified  by  the
          	 tuxTmachineTuxConfig attribute value  on  the  master  machine.
          	 The information contained in this file is automatically
          	 propagated to all other tuxTmachineTable objects as  they  are
          	 activated.   See  tuxTmachineEnvFile  below for a discussion of
          	 how this attribute value is used in the environment. "
     ::=  { tuxTmachineEntry 3 }

tuxTmachineTuxDir   OBJECT-TYPE
     SYNTAX  DisplayString (SIZE (2..256))
     ACCESS  read-write
     STATUS  mandatory
     DESCRIPTION 
               " Absolute pathname of the  directory  where  the  TUXEDO
          	 System/T  software  is  found  on  this  machine.   See
          	 tuxTmachineEnvFile below for a discussion of how this 
		 attribute value is used in the environment. "
     ::=  { tuxTmachineEntry 4 }

tuxTmachineAppDir   OBJECT-TYPE
     SYNTAX  DisplayString (SIZE (2..256))
     ACCESS  read-write
     STATUS  mandatory
     DESCRIPTION 
               " Colon separated list of application directory  absolute
            	 pathnames.   The  first directory serves as the current
           	 directory  for  all  application   and   administrative
           	 servers booted on this machine.  All directories in the
           	 list are searched when  starting  application  servers.
           	 See  tuxTmachineEnvFile  below  for  a  discussion  of how this
           	 attribute value is used in the environment. "
     ::=  { tuxTmachineEntry 5 }

tuxTmachineState   OBJECT-TYPE
     SYNTAX  INTEGER {
			active(1),
			inactive(2),
			partitioned(3),
			invalid(4),
			re-activate(5),
			cleaning(7)
		}
     ACCESS  read-write
     STATUS  mandatory
     DESCRIPTION 
               " GET:
               A GET operation will  retrieve  configuration  and
               runtime  information  for  the  selected tuxTmachineTable
               instance(s).   The  following  states  indicate  the
               meaning  of a tuxTmachinState returned in response to a
               GET  request.   States  not  listed  will  not  be
               returned.

               active(1)    tuxTmachineTable instance defined  and  active
                            (administrative   servers,  that  is,
                            DBBL, BBL, and BRIDGE).

               inactive(2)  tuxTmachineTable instance  defined  and  inac-
                            tive.

               partitioned(3)
			    tuxTmachineTable instance defined,  listed  in
                            accessible bulletin boards as active,
                            but  currently   unreachable.

          
          SET: A SET operation will update configuration and run-
               time  information  for  the   selected   tuxTmachineTable
               instance.  The following states indicate the meaning
               of a tuxTmachinState set in a SET  request.   States  not
               listed may not be set.


               invalid(4)   Delete tuxTmachineTable instance for  applica-
                            tion.  State change allowed only when
                            in the  inactive(2)  state.   Successful
                            return   leaves  the  object  in  the
                            invalid(4) state.
               active(1)    Activate   the   tuxTmachineTable  instance.
                            Necessary administrative servers such
                            as the  DBBL,  BBL,  and  BRIDGE  are
                            started on the indicated site as well
                            as application servers configured  to
                            run on that site.  State  change
                            allowed  only  when  in  the inactive(2)
                            state.  Successful return leaves  the
                            object in the active(1) state.

               re-activate(5)
			    Activate   the   tuxTmachineTable  instance.
                            Necessary administrative servers such
                            as the  DBBL,  BBL,  and  BRIDGE  are
                            started on the indicated site as well
                            as application servers configured  to
                            run on that site State  change
                            allowed   only  when  in  either  the
                            active(1) or inactive(2) state. Successful
                            return   leaves  the  object  in  the
                            active(1) state.

               inactive(2)  Deactivate  the   tuxTmachineTable instance.
                            Necessary administrative servers such
                            as the BBL and BRIDGE are stopped  on
                            the  indicated site as well as appli-
                            cation servers running on  that  site
                            State change allowed only when in the 
			    active(1) state and when no other appl-
			    ication resources are active on the indicated  
			    machine.  Successful return leaves  the  
			    object in the inactive(2) state.


               cleaning(7)  Initiate cleanup/scanning  activities
                            on  and  relating  to  the  indicated
                            machine.  If there are  dead  clients
                            or  servers on the machine, they will
                            be detected at  this  time.   If  the
                            machine has been partitioned from the
                            application MASTER site, then  global
                            bulletin   board   entries  for  that
                            machine will be removed.  This combi-
                            nation  is  allowed when the applica-
                            tion is in the active(1) state  and  the
                            tuxTmachineTable instance is in either the
                            active(1) or  partitioned(3) state. Suc-
                            cessful  return for a non-partitioned
                            machine leaves the  state  unchanged.
                            Successful  return  for a partitioned
                            machine  leaves  the  object  in  the
                            inactive(2) state.

          Limitation: State change to force-inactive(6) or inactive(2)
          allowed  only for non-master machines.  The master site
          administrative  processes  are  deactivated   via   the
          tuxTdomain group. "
     ::=  { tuxTmachineEntry 6 }


tuxTmachineUid   OBJECT-TYPE
     SYNTAX  INTEGER
     ACCESS  read-write
     STATUS  mandatory
     DESCRIPTION 
               " UNIX System user identifier  for  the  TUXEDO  System/T
          	 application administrator on this machine.  Administra-
          	 tive commands such  as  tmboot(1),  tmshutdown(1),  and
          	 tmadmin(1)  must  run  as  the  indicated  user on this
          	 machine.  Application  and  administrative  servers  on
          	 this machine will be started as this user.
          	 Limitation: This is a  UNIX  System-specific  attribute
          	 that  may  not be returned if the platform on which the
          	 application is being run is not UNIX-based. "
     ::=  { tuxTmachineEntry 7 }

tuxTmachineGid   OBJECT-TYPE
     SYNTAX  INTEGER
     ACCESS  read-write
     STATUS  mandatory
     DESCRIPTION 
               " UNIX System group identifier for  the  TUXEDO  System/T
          	 application administrator on this machine.  Administra-
          	 tive commands such  as  tmboot(1),  tmshutdown(1),  and
          	 tmadmin(1)  must  run as part of the indicated group on
          	 this machine.  Application and  administrative  servers
          	 on this machine will be started as part of this group.
          	 Limitation: This is a  UNIX  System-specific  attribute
          	 that  may  not be returned if the platform on which the
          	 application is being run is not UNIX-based. "
     ::=  { tuxTmachineEntry 8 }

tuxTmachineEnvFile   OBJECT-TYPE
     SYNTAX  DisplayString (SIZE (2..256))
     ACCESS  read-write
     STATUS  mandatory
     DESCRIPTION 
               " Environment file for clients  and  servers  running  on
          	 this  machine.  "
     ::=  { tuxTmachineEntry 9 }

tuxTmachinePerm   OBJECT-TYPE
     SYNTAX  DisplayString (SIZE(4))
     ACCESS  read-write
     STATUS  mandatory
     DESCRIPTION 
               "  UNIX System  permissions  associated  with  the  shared
          	 memory bulletin board created on this machine.  Default
          	 UNIX System permissions for system and application mes-
          	 sage queues.
		 Format: 0ddd, where d is a number 0 through 7. 
          	 Limitations: Modifications to  this  attribute  for  an
          	 active  object  will  not  affect  running  servers  or
          	 clients.
          	 This is a UNIX System-specific attribute that  may  not
          	 be returned if the platform on which the application is
          	 being run is not UNIX-based. "
     ::=  { tuxTmachineEntry 10 }

tuxTmachineUlogPfx   OBJECT-TYPE
     SYNTAX  DisplayString (SIZE (0..256))
     ACCESS  read-write
     STATUS  mandatory
     DESCRIPTION 
               " Absolute pathname prefix of the path for the userlog(3)
          	 file  on  this  machine.   The  userlog(3) file name is
          	 formed  by  appending  the  string   .mmddyy   to  this
          	 variable.   mmddyy  represents  the
          	 month, day, and year that the messages were  generated.
          	 All  application  and  system  userlog(3) messages gen-
          	 erated by clients and servers running on  this  machine
          	 are directed to this file.
          	 Limitation: Modifications  to  this  attribute  for  an
          	 active  object  will  not  affect  running  servers  or
          	 clients. "
     ::=  { tuxTmachineEntry 11 }

tuxTmachineType   OBJECT-TYPE
     SYNTAX  DisplayString (SIZE (1..15))
     ACCESS  read-write
     STATUS  mandatory
     DESCRIPTION 
               " Machine type.  Used to group machines into  classes  of
          	 like  data  representations.  Data encoding is not per-
          	 formed when communicating between machines of identical
          	 types.   This  attribute can be given any string value;
          	 values are used only for comparison.  Distinct  
		 tuxTmachineType attributes should be set when the 
		 application spans a heterogeneous network of  machines  or  
		 when  compilers generate  dissimilar  structure  
		 representations.   The default value for this attribute,  
		 a  0-length  string, matches any other machine with a 
		 0-length string as its tuxTmachineType attribute value. "
     ::=  { tuxTmachineEntry 12 }

tuxTmachineMaxAccessers   OBJECT-TYPE
     SYNTAX  INTEGER (1..32767)
     ACCESS  read-write
     STATUS  mandatory
     DESCRIPTION 
               " Maximum number of clients and  servers  that  can  have
          	 access  to  the  bulletin  board on this machine at one
          	 time.  System administration processes such as the  BBL
          	 and  tmadmin  need not be accounted for in this figure,
          	 but all application servers and clients and TMS servers
          	 should  be  counted.   If  the  application  is booting
          	 workstation listeners  on  this  site,  then  both  the
          	 listeners  and  the  potential  number  of  workstation
          	 handlers that may be booted should be counted. "
     ::=  { tuxTmachineEntry 13 }

tuxTmachineMaxConv   OBJECT-TYPE
     SYNTAX  INTEGER (0..32767)
     ACCESS  read-write
     STATUS  mandatory
     DESCRIPTION 
               " Maximum number of simultaneous conversations  in  which
          	 clients and servers on this machine can be involved. "
     ::=  { tuxTmachineEntry 14 }

tuxTmachineMaxGtt   OBJECT-TYPE
     SYNTAX  INTEGER (0..32767)
     ACCESS  read-write
     STATUS  mandatory
     DESCRIPTION 
               " Maximum number of simultaneous global  transactions  in
          	 which this machine can be involved. "
     ::=  { tuxTmachineEntry 15 }

tuxTmachineMaxWsClients   OBJECT-TYPE
     SYNTAX  INTEGER (0..32767)
     ACCESS  read-write
     STATUS  mandatory
     DESCRIPTION 
               " Number of  accesser  entries  on  this  machine  to  be
          	 reserved for workstation clients.  The number specified
          	 here takes a portion of the total accesser slots speci-
          	 fied with the tuxTmachineMaxAccessers object. The appropri-
          	 ate setting of this parameter  helps  to  conserve  IPC
          	 resources since workstation client access to the system
          	 is multiplexed through a System/T  supplied  surrogate,
          	 the  workstation  handler.   It is an error to set this
          	 number greater than tuxTmachineMaxAccessers. "
     ::=  { tuxTmachineEntry 16 }

tuxTmachineMaxAclCache   OBJECT-TYPE
     SYNTAX  INTEGER (10..32000)
     ACCESS  read-write
     STATUS  mandatory
     DESCRIPTION 
               " Number of entries in the cache  used  for  ACL  entries
          	 when  tuxTdomainSecurity is set to acl(4) or mandatory-
		 acl(5).  The appropriate setting of this parameter helps 
		 to conserve on shared memory resources and yet reduce the 
		 number of disk access to do ACL checking. "
     ::=  { tuxTmachineEntry 17 }

tuxTmachineTlogDevice   OBJECT-TYPE
     SYNTAX  DisplayString (SIZE (0..256))
     ACCESS  read-write
     STATUS  mandatory
     DESCRIPTION 
               " The device (raw slice) or UNIX System  file  containing
          	 the TUXEDO System/T filesystem that holds the DTP tran-
          	 saction log for this machine.  The DTP transaction  log
          	 is  stored  as a TUXEDO System/T VTOC table on the dev-
          	 ice.  This device or file  may  be  the  same  as  that
          	 specified  for  the  tuxTmachineTuxConfig  attribute  for  
		 this machine. "
     ::=  { tuxTmachineEntry 18 }

tuxTmachineTlogName   OBJECT-TYPE
     SYNTAX  DisplayString (SIZE (0..30))
     ACCESS  read-write
     STATUS  mandatory
     DESCRIPTION 
               " The name of the DTP transaction log for  this  machine.
          	 If more than one DTP transaction log exists on the same
          	 tuxTmachineTlogDevice,   they   must   have    unique    
		 names.
          	 tuxTmachineLogName  must  be  different  from  the name 
		 of any other table on the tuxTmachineTlogDevice where the 
		 DTP transaction log table is created. "
     ::=  { tuxTmachineEntry 19 }

tuxTmachineTlogSize   OBJECT-TYPE
     SYNTAX  INTEGER (1..2048)
     ACCESS  read-write
     STATUS  mandatory
     DESCRIPTION 
               " The numeric size, in pages, of the DTP transaction  log
          	 for  this  machine.  The tuxTmachineLogSize attribute value 
		 is subject to limits based on available space in the  TUX-
          	 EDO System/T filesystem identified by the tuxTmachineTlog-
		 Device object. "
     ::=  { tuxTmachineEntry 20 }

tuxTmachineBridge   OBJECT-TYPE
     SYNTAX  DisplayString (SIZE (0..78))
     ACCESS  read-write
     STATUS  mandatory
     DESCRIPTION 
               " Device name to be used by the BRIDGE process placed  on
          	 this  logical machine to access the network.  This is a
          	 required value for participation in a networked  appli-
          	 cation  via  a  TLI-based TUXEDO System/T binary.  This
          	 attribute  is  not  needed  for  sockets-based   TUXEDO
          	 System/T binaries. "
     ::=  { tuxTmachineEntry 21 }

tuxTmachineNaddr   OBJECT-TYPE
     SYNTAX  DisplayString (SIZE (0..256))
     ACCESS  read-write
     STATUS  mandatory
     DESCRIPTION 
               " Specifies the complete network address to  be  used  by
          	 the BRIDGE process placed on the logical machine as its
          	 listening address.  The listening address for a  BRIDGE
          	 is  the  means by which it is contacted by other BRIDGE
          	 processes  participating  in  the  application.    This
          	 attribute must be set if the logical machine is to par-
          	 ticipate in a networked application, that  is,  if  the
          	 Lan  option is set in the tuxTdomainOptions object value.
          	 If string has the form  ``0xhex-digits''  or  ``\\xhex-
          	 digits'',  it  must contain an even number of valid hex
          	 digits.  These forms are translated internally  into  a
          	 character  array containing the hexadecimal representa-
          	 tions of the string specified. " 
     ::=  { tuxTmachineEntry 22 }

tuxTmachineNlsaddr   OBJECT-TYPE
     SYNTAX  DisplayString (SIZE (0..256))
     ACCESS  read-write
     STATUS  mandatory
     DESCRIPTION 
               " Network address used by the tlisten(1) process  servic-
          	 ing  the network on the node identified by this logical
          	 machine.  This network address is of the same format as
          	 that specified for the tuxTmachineNaddr attribute above.
          	 This attribute must be set if the logical machine is to
          	 participate in a networked application, that is, if the
          	 Lan option is set in the tuxTdomainOptions  object
          	 value. "
     ::=  { tuxTmachineEntry 23 }

tuxTmachineCmpLimit	OBJECT-TYPE
     SYNTAX  DisplayString
     ACCESS  read-write
     STATUS  mandatory
     DESCRIPTION 
               " Threshold message size at which compression will occur for 
	   remote traffic and optionally local traffic.  remote and local may 
	   be either non-negative numeric values or the string ``MAXLONG'',
           which is dynamically translated to the maximum long setting for
           the machine.  Setting only the remote value will default local to
           MAXLONG.

           Limitation: This attribute value is not part of the tuxTmachineTable
           object for active sites running TUXEDO System/T Release 4.2.2 or
           earlier.  However, site release identification is not determined
           until runtime, so this attribute may be set and accessed for any
           inactive object.  When a TUXEDO System/T Release 4.2.2 or earlier
           site is activated, the configured value is not used. "
     ::=  { tuxTmachineEntry 24 }

tuxTmachineTmNetLoad   OBJECT-TYPE
     SYNTAX  INTEGER (0..32767)
     ACCESS  read-write
     STATUS  mandatory
     DESCRIPTION 
               " Service load added to any remote service evaluated dur-
          	 ing load balancing on this machine.
          	 Limitation: This attribute value is  not  part  of  the
          	 tuxTmachineTable   object  for  active  sites  running  TUXEDO
          	 System/T  Release  4.2.2  or  earlier.   However,  site
          	 release identification is not determined until runtime,
          	 so this attribute may be set and accessed for any inac-
          	 tive  object.   When a TUXEDO System/T Release 4.2.2 or
          	 earlier site is activated, the configured value is  not
          	 used. "
     ::=  { tuxTmachineEntry 25 }

tuxTmachineSpinCount   OBJECT-TYPE
     SYNTAX  INTEGER
     ACCESS  read-write
     STATUS  mandatory
     DESCRIPTION 
               " Spincount used on  this  machine  for  pre-ticket  user
          	 level  semaphore access.  Default values are built into
          	 the TUXEDO System/T binaries on  each  machine.   These
          	 defaults  may  be overridden at runtime for tuning pur-
          	 poses using this attribute.  The spincount may be reset
          	 to the default built-in value for the site by resetting
          	 this attribute value to 0.
          	 Limitation: This attribute value is  not  part  of  the
          	 tuxTmachineTable   object  for  active  sites  running  TUXEDO
          	 System/T  Release  4.2.2  or  earlier.   However,  site
          	 release identification is not determined until runtime,
          	 so this attribute may be set and accessed for any inac-
          	 tive  object.   When a TUXEDO System/T Release 4.2.2 or
          	 earlier site is activated, the configured value is  not
          	 used. "
     ::=  { tuxTmachineEntry 26 }

tuxTmachineRole   OBJECT-TYPE
     SYNTAX  INTEGER {
			master(1),
			backup(2),
			other(3)
		}
     ACCESS  read-only
     STATUS  mandatory
     DESCRIPTION 
               " The role of this machine in  the  application.   MASTER
          	 indicates  that  this  machine  is  the master machine,
          	 BACKUP indicates that it is the backup master  machine,
          	 and  OTHER  indicates  that  the machine is neither the
          	 master nor backup master machine. "
     ::=  { tuxTmachineEntry 27 }

tuxTmachineMinor   OBJECT-TYPE
     SYNTAX  INTEGER
     ACCESS  read-only
     STATUS  mandatory
     DESCRIPTION 
               " The TUXEDO System/T minor protocol release  number  for
          	 this machine. "
     ::=  { tuxTmachineEntry 28 }

tuxTmachineRelease   OBJECT-TYPE
     SYNTAX  INTEGER
     ACCESS  read-only
     STATUS  mandatory
     DESCRIPTION 
               " The TUXEDO System/T major protocol release  number  for
          	 this   machine.    This   may  be  different  from  the
          	 tuxTmachineSWRelease for the same machine. "
     ::=  { tuxTmachineEntry 29 }

tuxTmachineMaxPendingBytes   OBJECT-TYPE
     SYNTAX  INTEGER
     ACCESS  read-write
     STATUS  mandatory
     DESCRIPTION 
               " This object specifies a limit for the amount of space that
		 can be allocated for messages waiting to be transmitted by
		 the BRIDGE process.
		 The minimum value for this is 100000.
		 SUPPORT: Tuxedo 6.4 and later versions only."
     ::=  { tuxTmachineEntry 30 }

 
tuxMachineMaxObjects   OBJECT-TYPE
     SYNTAX  INTEGER
     ACCESS  read-write
     STATUS  mandatory
     DESCRIPTION
               " The maximum number of objects to be accommodated in the
                 Active Object Map tables in the bulletin board."
     ::=  { tuxTmachineEntry 35 }

-- Added : BEGIN-JANUS-NS-TUXEDO7.1-041400

tuxTmachineEncryptionRequired   OBJECT-TYPE
     SYNTAX  INTEGER {
		yes(1),
		no(2)
	}
     ACCESS  read-write
     STATUS  mandatory
     DESCRIPTION 
	 "If set to 'yes', every application service on this machine requires an
     encrypted input message buffer. 
		 SUPPORT: Tuxedo 7.1 and later versions only."
     ::=  { tuxTmachineEntry 50 }

tuxTmachineSignatureRequired   OBJECT-TYPE
     SYNTAX  INTEGER {
		yes(1),
		no(2)
	}
     ACCESS  read-write
     STATUS  mandatory
     DESCRIPTION 
	"If set to 'yes', every application service on this machine requires a
     valid digital signature on its input message buffer. 
		 SUPPORT: Tuxedo 7.1 and later versions only."
     ::=  { tuxTmachineEntry 60 }

-- Added : END-JANUS-NS-TUXEDO7.1-041400

-- **********************************************************************
-- tuxTmachineActive group
-- This group represents run-time statistics on the local machine if it
-- is active i.e. some component of the application is active on the
-- machine.
--
-- NOTE: All objects in this MIB group are local attributes i.e.
--       values for these objects correspond to the local host
--       only, where the TUXEDO agent is running. So the user needs
--       to run an instance of the TUXEDO agent on every node for
--       which these values are of interest."
-- **********************************************************************


tuxTmachineActive OBJECT IDENTIFIER ::= { tuxTmachine 2 }

tuxTmachineCurAccessers   OBJECT-TYPE
     SYNTAX  INTEGER (0..32767)
     ACCESS  read-only
     STATUS  mandatory
     DESCRIPTION 
               " Number of clients and servers currently  accessing  the
          	 application  either directly on this machine or through
          	 a workstation handler on this machine. "
     ::=  { tuxTmachineActive 1 }

tuxTmachineCurClients   OBJECT-TYPE
     SYNTAX  INTEGER (0..32767)
     ACCESS  read-only
     STATUS  mandatory
     DESCRIPTION 
               " Number  of  clients,  both  native   and   workstation,
          	 currently logged in to this machine. "
     ::=  { tuxTmachineActive 2 }

tuxTmachineCurConv   OBJECT-TYPE
     SYNTAX  INTEGER (0..32767)
     ACCESS  read-only
     STATUS  mandatory
     DESCRIPTION 
               " Number of active  conversations  with  participants  on
          	 this machine. "
     ::=  { tuxTmachineActive 3 }

tuxTmachineCurGTT   OBJECT-TYPE
     SYNTAX  INTEGER (0..32767)
     ACCESS  read-only
     STATUS  mandatory
     DESCRIPTION 
               " Number of in use  transaction  table  entries  on  this
          	 machine. "
     ::=  { tuxTmachineActive 4 }

tuxTmachineCurLoad   OBJECT-TYPE
     SYNTAX  INTEGER
     ACCESS  read-only
     STATUS  mandatory
     DESCRIPTION 
               " Current service load enqueued on this machine.
          	 Limitation: If the tuxTdomainLoadBalance attribute is no(2)
          	 or  the  tuxTdomainModel attribute is multi-machine(2), 
		 then an FML32 NULL value is returned (0). "
     ::=  { tuxTmachineActive 5 }

tuxTmachineCurWsClients   OBJECT-TYPE
     SYNTAX  INTEGER (0..32767)
     ACCESS  read-only
     STATUS  mandatory
     DESCRIPTION 
               " Number of workstation clients currently  logged  in  to
          	 this machine. "
     ::=  { tuxTmachineActive 6 }

tuxTmachineHwAccessers   OBJECT-TYPE
     SYNTAX  INTEGER (0..32767)
     ACCESS  read-only
     STATUS  mandatory
     DESCRIPTION 
               "  High water number of clients and servers accessing  the
          	 application  either directly on this machine or through
          	 a workstation handler on this machine. "
     ::=  { tuxTmachineActive 7 }

tuxTmachineHwClients   OBJECT-TYPE
     SYNTAX  INTEGER (0..32767)
     ACCESS  read-only
     STATUS  mandatory
     DESCRIPTION 
               " High water number of clients, both native and  worksta-
          	 tion, logged in to this machine. "
     ::=  { tuxTmachineActive 8 }

tuxTmachineHwConv   OBJECT-TYPE
     SYNTAX  INTEGER (0..32767)
     ACCESS  read-only
     STATUS  mandatory
     DESCRIPTION 
               " High water number of active conversations with partici-
          	 pants on this machine. "
     ::=  { tuxTmachineActive 9 }

tuxTmachineHwGTT   OBJECT-TYPE
     SYNTAX  INTEGER (0..32767)
     ACCESS  read-only
     STATUS  mandatory
     DESCRIPTION 
               " High water number of in use transaction  table  entries
          	 on this machine. "
     ::=  { tuxTmachineActive 10 }

tuxTmachineHwWsClients   OBJECT-TYPE
     SYNTAX  INTEGER (0..32767)
     ACCESS  read-only
     STATUS  mandatory
     DESCRIPTION 
               " High water  number  of  workstation  clients  currently
          	 logged in to this machine. "
     ::=  { tuxTmachineActive 11 }

tuxTmachineNumConv   OBJECT-TYPE
     SYNTAX  INTEGER
     ACCESS  read-only
     STATUS  mandatory
     DESCRIPTION 
               " Number of tpconnect(3) operations performed  from  this
          	 machine. "
     ::=  { tuxTmachineActive 12 }

tuxTmachineNumDequeue   OBJECT-TYPE
     SYNTAX  INTEGER
     ACCESS  read-only
     STATUS  mandatory
     DESCRIPTION 
               " Number of tpdequeue(3) operations performed  from  this
          	 machine. "
     ::=  { tuxTmachineActive 13 }

tuxTmachineNumEnqueue   OBJECT-TYPE
     SYNTAX  INTEGER
     ACCESS  read-only
     STATUS  mandatory
     DESCRIPTION 
               " Number of tpenqueue(3) operations performed  from  this
          	 machine. "
     ::=  { tuxTmachineActive 14 }

tuxTmachineNumPost   OBJECT-TYPE
     SYNTAX  INTEGER
     ACCESS  read-only
     STATUS  mandatory
     DESCRIPTION 
               " Number of  tppost(3)  operations  performed  from  this
          	 machine. "
     ::=  { tuxTmachineActive 15 }

tuxTmachineNumReq   OBJECT-TYPE
     SYNTAX  INTEGER
     ACCESS  read-only
     STATUS  mandatory
     DESCRIPTION 
               " Number of tpacall(3) or tpcall(3) operations  performed
          	 from this machine. "
     ::=  { tuxTmachineActive 16 }

tuxTmachineNumSubscribe   OBJECT-TYPE
     SYNTAX  INTEGER
     ACCESS  read-only
     STATUS  mandatory
     DESCRIPTION 
               " Number of tpsubscribe(3) operations performed from this
          	 machine. "
     ::=  { tuxTmachineActive 17 }

tuxTmachineNumTran   OBJECT-TYPE
     SYNTAX  INTEGER
     ACCESS  read-only
     STATUS  mandatory
     DESCRIPTION 
               " Number of transactions initiated (tpbegin(3)) from this
          	 machine. "
     ::=  { tuxTmachineActive 18 }

tuxTmachineNumTranAbt   OBJECT-TYPE
     SYNTAX  INTEGER
     ACCESS  read-only
     STATUS  mandatory
     DESCRIPTION 
               " Number of transactions aborted (tpabort(3))  from  this
          	 machine. "
     ::=  { tuxTmachineActive 19 }

tuxTmachineNumTranCmt   OBJECT-TYPE
     SYNTAX  INTEGER
     ACCESS  read-only
     STATUS  mandatory
     DESCRIPTION 
               " Number of  transactions  committed  (tpcommit(3))  from
          	 this machine. "
     ::=  { tuxTmachineActive 20 }

tuxTmachineLicExpires   OBJECT-TYPE
     SYNTAX  DisplayString (SIZE(0..78))
     ACCESS  read-only
     STATUS  mandatory
     DESCRIPTION 
               " Expiration date for the binary on that machine or a  0-
          	 length string if binary is not a TUXEDO System/T master
          	 binary. "
     ::=  { tuxTmachineActive 21 }

tuxTmachineLicMaxUsers   OBJECT-TYPE
     SYNTAX  INTEGER (0..32767)
     ACCESS  read-only
     STATUS  mandatory
     DESCRIPTION 
               " Licensed maximum number of users on that machine or  -1
          	 if binary is not a TUXEDO System/T master binary. "
     ::=  { tuxTmachineActive 22 }

tuxTmachineLicSerial   OBJECT-TYPE
     SYNTAX  DisplayString (SIZE(0..78))
     ACCESS  read-only
     STATUS  mandatory
     DESCRIPTION 
               " Serial number for binary on that machine or a  0-length
          	 string  if  binary  is  not  a  TUXEDO  System/T master
          	 binary. "
     ::=  { tuxTmachineActive 23 }

tuxTmachinePageSize   OBJECT-TYPE
     SYNTAX  INTEGER
     ACCESS  read-only
     STATUS  mandatory
     DESCRIPTION 
               " Disk pagesize used on this machine. " 
     ::=  { tuxTmachineActive 24 }

tuxTmachineSWrelease   OBJECT-TYPE
     SYNTAX  DisplayString (SIZE(0..78))
     ACCESS  read-only
     STATUS  mandatory
     DESCRIPTION 
               " Software release for binary on that  machine  or  a  0-
          	 length string if binary is not a TUXEDO System/T master
	  	 binary."
     ::=  { tuxTmachineActive 25 }

tuxTmachineHwAclCache   OBJECT-TYPE
     SYNTAX  INTEGER
     ACCESS  read-only
     STATUS  mandatory
     DESCRIPTION 
               " High water number of entries used in the ACL cache. "
     ::=  { tuxTmachineActive 26 }

tuxTmachineAclCacheHits   OBJECT-TYPE
     SYNTAX  INTEGER
     ACCESS  read-only
     STATUS  mandatory
     DESCRIPTION 
               " Number of accesses to the ACL cache that resulted in  a
          	 `hit' (that is, the entry was already in the cache). "
     ::=  { tuxTmachineActive 27 }

tuxTmachineAclCacheAccess   OBJECT-TYPE
     SYNTAX  INTEGER
     ACCESS  read-only
     STATUS  mandatory
     DESCRIPTION 
               " Number of accesses to the ACL cache. "
     ::=  { tuxTmachineActive 28 }

tuxTmachineAclFail   OBJECT-TYPE
     SYNTAX  INTEGER
     ACCESS  read-only
     STATUS  mandatory
     DESCRIPTION 
               " Number of accesses to the ACL cache that resulted in  a
          	 access control violation. "
     ::=  { tuxTmachineActive 29 }

tuxTmachineWkCompleted   OBJECT-TYPE
     SYNTAX  INTEGER
     ACCESS  read-only
     STATUS  mandatory
     DESCRIPTION 
               " Total service load dequeued and processed  successfully
          	 by servers running on this machine.  Note that for long
          	 running applications  this  attribute  may  wraparound,
          	 that is, exceed the maximum value for a long, and start
          	 back at 0 again. "
     ::=  { tuxTmachineActive 30 }

tuxTmachineWkInitiated   OBJECT-TYPE
     SYNTAX  INTEGER
     ACCESS  read-only
     STATUS  mandatory
     DESCRIPTION 
               " Total service load enqueued by clients/servers  running
          	 on  this  machine.  Note that for long running applica-
          	 tions this attribute may wraparound,  that  is,  exceed
          	 the  maximum  value  for  a  long,  and start back at 0
          	 again. "
     ::=  { tuxTmachineActive 31 }

tuxMachineCurObjects   OBJECT-TYPE
     SYNTAX  INTEGER
     ACCESS  read-only
     STATUS  mandatory
     DESCRIPTION
               " The number of entries in use in the bulletin board object
                 table for this machine."
     ::=  { tuxTmachineActive 36 }
 
tuxMachineHwObjects   OBJECT-TYPE
     SYNTAX  INTEGER
     ACCESS  read-only
     STATUS  mandatory
     DESCRIPTION
               " The high water number of entries used in the bulletin board
                 object table for this machine. "
     ::=  { tuxTmachineActive 41 }

-- **************************************************************************
-- tuxTmsg Group
-- The tuxTmsg group represents runtime attributes of the  TUXEDO
-- System/T managed UNIX System message queues.
-- **************************************************************************

tuxTmsgTable OBJECT-TYPE
     SYNTAX  SEQUENCE OF TuxTmsgEntry
     ACCESS   not-accessible
     STATUS  mandatory
     DESCRIPTION 
               " Tuxedo message queue table"
     ::= { tuxTmsg 1 }

tuxTmsgEntry OBJECT-TYPE
     SYNTAX  TuxTmsgEntry
     ACCESS  not-accessible 
     STATUS  mandatory
     DESCRIPTION 
               "Row of tuxTmsgTable.

		NOTE: All objects in this MIB group are local attributes i.e.
		      values for these objects correspond to the local host
		      only, where the TUXEDO agent is running. So the user needs
		      to run an instance of the TUXEDO agent on every node for
		      which these values are of interest."
     INDEX { tuxTmsgId }
     ::= { tuxTmsgTable 1 }

TuxTmsgEntry ::= SEQUENCE {
     tuxTmsgId
       INTEGER,
     tuxTmsgState
        INTEGER,
     tuxTmsgCurTime
        INTEGER,
     tuxTmsgCbytes
        INTEGER,
     tuxTmsgCtime
        INTEGER,
     tuxTmsgLrPid
	INTEGER,
     tuxTmsgLsPid
	INTEGER,
     tuxTmsgQbytes
	INTEGER,
     tuxTmsgQnum
	INTEGER,
     tuxTmsgRtime
	INTEGER,
     tuxTmsgStime
	INTEGER
     }   

tuxTmsgId   OBJECT-TYPE
     SYNTAX  INTEGER
     ACCESS  read-only
     STATUS  mandatory
     DESCRIPTION 
               " UNIX System message queue identifier.
          	 Limitation: This is a  UNIX  System-specific  attribute
          	 that  may  not be returned if the platform on which the
          	 application is being run is not UNIX-based. "
     ::=  { tuxTmsgEntry 1 }

tuxTmsgState   OBJECT-TYPE
     SYNTAX  INTEGER {
			active(1)
		}
     ACCESS  read-only
     STATUS  mandatory
     DESCRIPTION 
               " GET:
               	 A GET operation will retrieve runtime  information
               	 for  the  selected tuxTmsgTbl instance(s).  The following
               	 states indicate the meaning of a tuxTmsgState returned
               	 in  response  to a GET request.  States not listed
               	 will not be returned.

               	 active(1)  tuxTmsgTbl instance active. This
                            corresponds  exactly  to  the related
                            tuxTmachineTable object being active. "
     ::=  { tuxTmsgEntry 2 }

tuxTmsgCurTime   OBJECT-TYPE
     SYNTAX  INTEGER
     ACCESS  read-only
     STATUS  mandatory
     DESCRIPTION 
               " Current time, in seconds, since 00:00:00  UTC,  January
          	 1,  1970,  as  returned  by  the time(2) system call on
          	 the local host.  "
     ::=  { tuxTmsgEntry 3 }

tuxTmsgCbytes   OBJECT-TYPE
     SYNTAX  INTEGER
     ACCESS  read-only
     STATUS  mandatory
     DESCRIPTION 
               " Current number of bytes on the queue. "
     ::=  { tuxTmsgEntry 4 }

tuxTmsgCtime   OBJECT-TYPE
     SYNTAX  INTEGER
     ACCESS  read-only
     STATUS  mandatory
     DESCRIPTION 
               " Time of the last msgctl(2)  operation  that  changed  a
          	 member of  the  msqid_ds structure associated with the
          	 queue. "
     ::=  { tuxTmsgEntry 5 }

tuxTmsgLrPid   OBJECT-TYPE
     SYNTAX  INTEGER
     ACCESS  read-only
     STATUS  mandatory
     DESCRIPTION 
               " Process identifier of the last process that  read  from
          	 the queue. "
     ::=  { tuxTmsgEntry 6 }

tuxTmsgLsPid   OBJECT-TYPE
     SYNTAX  INTEGER
     ACCESS  read-only
     STATUS  mandatory
     DESCRIPTION 
               " Process identifier of the last process  that  wrote  to
          	 the queue. "
     ::=  { tuxTmsgEntry 7 }

tuxTmsgQbytes   OBJECT-TYPE
     SYNTAX  INTEGER
     ACCESS  read-only
     STATUS  mandatory
     DESCRIPTION 
               " Maximum number of bytes allowed on the queue. "
     ::=  { tuxTmsgEntry 8 }

tuxTmsgQnum   OBJECT-TYPE
     SYNTAX  INTEGER
     ACCESS  read-only
     STATUS  mandatory
     DESCRIPTION 
               " Number of messages currently on the queue. "
     ::=  { tuxTmsgEntry 9 }

tuxTmsgRtime   OBJECT-TYPE
     SYNTAX  INTEGER
     ACCESS  read-only
     STATUS  mandatory
     DESCRIPTION 
               " Time since the last read from the queue. "
     ::=  { tuxTmsgEntry 10 }

tuxTmsgStime   OBJECT-TYPE
     SYNTAX  INTEGER
     ACCESS  read-only
     STATUS  mandatory
     DESCRIPTION 
               " Time since the last write to the queue. "
     ::=  { tuxTmsgEntry 11 }

-- ************************************************************************
-- tuxTqueue group
-- The tuxTqueue group represents runtime attributes of queues in
-- an application.  These attribute values identify and charac-
-- terize allocated TUXEDO System/T request  queues  associated
-- with  servers  in  a  running  application.  They also track
-- statistics related to application workloads associated  with
-- each  queue object.
-- ************************************************************************

tuxTqueueTable OBJECT-TYPE
     SYNTAX  SEQUENCE OF TuxTqueueEntry
     ACCESS  not-accessible
     STATUS  mandatory
     DESCRIPTION
               " Tuxedo request queue table"
     ::= { tuxTqueue 1 }
 
tuxTqueueEntry OBJECT-TYPE
     SYNTAX  TuxTqueueEntry
     ACCESS  not-accessible 
     STATUS  mandatory
     DESCRIPTION
               "Row of tuxTqueueTable.

		NOTE:  All objects in this MIB group are local attributes i.e.
		       values for these objects correspond to the local host
		       only, where the TUXEDO agent is running. So the user needs
		       to run an instance of the TUXEDO agent on every node for
		       which these values are of interest."
     INDEX { tuxTqueueRqAddr }
     ::= { tuxTqueueTable 1 }
 
TuxTqueueEntry ::= SEQUENCE {
     tuxTqueueRqAddr
       DisplayString,
     tuxTqueueState
        INTEGER,
     tuxTqueueRqId
        INTEGER,
     tuxTqueueSrvrCnt
	INTEGER,
     tuxTqueueTotNqueued
	INTEGER,
     tuxTqueueTotWkQueued
	INTEGER,
     tuxTqueueSource
	DisplayString,
     tuxTqueueNqueued
	INTEGER,
     tuxTqueueWkQueued
	INTEGER
	}

tuxTqueueRqAddr   OBJECT-TYPE
     SYNTAX  DisplayString (SIZE(1..30))
     ACCESS  read-only		-- R
     STATUS  mandatory
     DESCRIPTION
               " Symbolic address of the request  queue.   Servers  with
          	 the same tuxTsrvrRqAddr object value are grouped
          	 into a Multiple Server Single Queue (MSSQ) set.  Attri-
          	 bute values returned with a tuxTqueueTable group apply to all
          	 active servers  associated  with  this  symbolic  queue
          	 address. "
     ::=  { tuxTqueueEntry 1 }

tuxTqueueState OBJECT-TYPE 
     SYNTAX  INTEGER {
		active(1),
		migrating(2),
		suspended(3),
		partitioned(4)
		} 
     ACCESS  read-only          -- R 
     STATUS  mandatory 
     DESCRIPTION 
               "            GET:
               A GET operation will retrieve runtime  information
               for  the  selected tuxTqueueTable instance(s).  The 
	       tuxTqueueTable group does not address  configuration  
	       information directly.   Configuration  related 
	       attributes discussed here must be set as part of the  
	       related tuxTsrvrTbl instances. The following states indicate
               the meaning of a tuxTqueueState returned in response  to
               a  GET  request.   States  not  listed will not be
               returned.

               active(1)    At least one server  associated  with
                            this tuxTqueueTable instance is active.

               migrating(2) The server(s)  associated  with  this
                            tuxTqueueTable instance is currently in the
                            migrating state. See  the  tuxTsrvrTbl
                            group for more details on this state.

               suspended(3) The server(s)  associated  with  this
                            tuxTqueueTable instance is currently in the
                            suspended state.   See  the  tuxTsrvrTbl
                            group for more details on this state.

               partitioned(4)  
			    The server(s)  associated  with  this
                            tuxTqueueTable instance is currently in the
                            partitioned state.  See the  tuxTsrvrTbl
                            group for more details on this state. "
     ::=  { tuxTqueueEntry 2 } 
 

tuxTqueueRqId   OBJECT-TYPE
     SYNTAX  INTEGER 
     ACCESS  read-only
     STATUS  mandatory
     DESCRIPTION
               " UNIX System message queue identifier.
          	 Limitation: This is a UNIX  System  specific  attribute
          	 that  may  not be returned if the platform on which the
          	 application is being run is not UNIX-based. "
     ::=  { tuxTqueueEntry 3 }
 
tuxTqueueSrvrCnt   OBJECT-TYPE
     SYNTAX  INTEGER 
     ACCESS  read-only
     STATUS  mandatory
     DESCRIPTION
               " Number of active servers associated with this queue. "
     ::=  { tuxTqueueEntry 4 }
 
tuxTqueueTotNqueued   OBJECT-TYPE
     SYNTAX  INTEGER 
     ACCESS  read-only
     STATUS  mandatory
     DESCRIPTION
               " The sum of the queue lengths of this queue while it has
          	 been  active.   This  sum includes requests enqueued to
          	 and processed by servers that are no longer  active  on
          	 the  queue.  Each time a new request is assigned to the
          	 queue, the sum is incremented  by  the  length  of  the
          	 queue immediately before the new request is enqueued.
          	 Limitation: If the tuxTdomainLoadBalance attribute is no(2) 
          	 or the tuxTdomainModel attribute is multi-machine(2), then
          	 tuxTqueueTotNqueued is not returned.  In the same configura-
          	 tion,  updates  to  this attribute are ignored.  Conse-
		 quently, when this value is returned, tuxTqueueSource is 
		 same as the local host. "
     ::=  { tuxTqueueEntry 5 }

tuxTqueueTotWkQueued   OBJECT-TYPE
     SYNTAX  INTEGER 
     ACCESS  read-only
     STATUS  mandatory
     DESCRIPTION
               " The sum of the workloads enqueued to this  queue  while
          	 it   has  been  active.   This  sum  includes  requests
          	 enqueued to and processed by servers that are no longer
          	 active  on  the  queue.   Each  time  a  new request is
          	 assigned to the queue, the sum is  incremented  by  the
          	 workload  on  the  queue  immediately  before  the  new
          	 request is enqueued.
          	 Limitation: If the tuxTdomainLoadBalance attribute  is no(2) 
          	 or   the  tuxTdomainModel  attribute  is  `MP',  then
          	 this variable is not meaningful.  In the same configura-
          	 tion,  updates  to  this attribute are ignored.  Conse-
          	 quently, when this attribute is  returned  tuxTqueueSource 
		 is the same as the local host. "
     ::=  { tuxTqueueEntry 6 }
 
tuxTqueueSource   OBJECT-TYPE
     SYNTAX  DisplayString (SIZE(1..30))
     ACCESS  read-only
     STATUS  mandatory
     DESCRIPTION
               " Logical machine from which local attribute  values  are
          	 retrieved. "
     ::=  { tuxTqueueEntry 7 }
 
tuxTqueueNqueued   OBJECT-TYPE
     SYNTAX  INTEGER 
     ACCESS  read-only
     STATUS  mandatory
     DESCRIPTION
               " Number of requests currently  enqueued  to  this  queue
          	 from  the  tuxTqueueSource logical machine. This value is
          	 incremented at enqueue time and  decremented when  the
          	 server dequeues the request.
          	 Limitation: If the tuxTdomainLoadBalance attribute  is no(2) 
          	 or   the  tuxTdomainModel attribute is multi-machine(2), then
          	 tuxTqueueNqueued is not returned. Consequently,  when  this
          	 attribute  is  returned  tuxTqueueSource is the sam as the
		 local host. "
     ::=  { tuxTqueueEntry 8 }
 
tuxTqueueWkQueued   OBJECT-TYPE
     SYNTAX  INTEGER 
     ACCESS  read-only
     STATUS  mandatory
     DESCRIPTION
               " Workload currently enqueued  to  this  queue  from  the
          	 tuxTqueueSource  logical  machine.   If the tuxTdomainModel
          	 attribute is set to single-machine(1) and the tuxTdomain-
		 LoadBalance attribute is set to yes(1) then this attribute 
		 reflects the application-wide workload enqueued to this 
		 queue. However, if tuxTdomainModel is set to MP and 
	  	 tuxTdomainLoadBalance is set to yes(1) , this attribute 
		 reflects the  workload enqueued to this queue from the 
		 tuxTqueueSource logical machine during a recent timespan.  
		 This attribute  is  used  for  load balancing  purposes.  
		 So as to not discriminate against newly started servers, 
		 this attribute value  is  zeroed out on each machine 
		 periodically by the BBL. "
     ::=  { tuxTqueueEntry 9 }

-- ***************************************************************************
-- tuxTrouting group
-- The tuxTroutingTable represents configuration  objects  of
-- routing  specifications for an application.  These object
-- values identify and characterize application data  dependent
-- routing  criteria with respect to field names, buffer types,
-- and routing definitions.
-- This table also represents configuration objects for Factory based routing 
-- in the case of a CORBA C++ Interface.
-- ***************************************************************************

tuxTroutingTable OBJECT-TYPE
     SYNTAX  SEQUENCE OF TuxTroutingEntry
     ACCESS  not-accessible
     STATUS  mandatory
     DESCRIPTION
               " Data dependent/Factory based routing specifications table."
     ::= { tuxTrouting 1 }

tuxTroutingEntry OBJECT-TYPE
     SYNTAX  TuxTroutingEntry
     ACCESS  not-accessible
     STATUS  mandatory
     DESCRIPTION
   " 1. tuxRoutingFieldType is valid only for factory based routing. 
   (CORBA C++ interface only)
	(beaRoutingType = factory(2) )

     2. tuxTroutingBufType is valid only for service based routing.
	(beaRoutingType = service(1) )

     3. Specifying Index in SET requests (including Row Creation):
	tuxInternalIdx is used as an index instead of tuxTroutingBufType/
	tuxTroutingField (for service/factory based routing respectively)
 	to reduce the size of the index.

	o tuxTroutingName and beaRoutingType should equal their actual values

   	Factory Based Routing: 
		 o tuxInternalIdx should always be equal to tuxTroutingField

 	Service Based Routing: 
		 o tuxInternalIdx should always equal the first 30 characters
		   in tuxTroutingBufType.

      4. Creation of a new row (instance): User needs to do a SET request for a
 	 non-existant row specifying values for all objects applicable to the 
	 beaRoutingType(note 1 and 2 above) except tuxTroutingState. See note 3
	 above for details on how to specify the index. " 

     INDEX { tuxTroutingName,beaRoutingType,tuxInternalIdx }

     ::= { tuxTroutingTable 1 }

TuxTroutingEntry ::= SEQUENCE {
     tuxTroutingName
       DisplayString,
     tuxTroutingBufType
        DisplayString,
     tuxTroutingField
        DisplayString,
     tuxTroutingRanges
        DisplayString,
     tuxTroutingState
        INTEGER,
     beaRoutingType
		INTEGER,
     tuxRoutingFieldType
		INTEGER,
     tuxInternalIdx
		DisplayString
     }

tuxTroutingName   OBJECT-TYPE
     SYNTAX  DisplayString (SIZE(1..15))
     ACCESS  read-write         -- writable only during row creation
     STATUS  mandatory
     DESCRIPTION
               " Routing criteria name.
                Note: This object can be set only during row creation."
     ::=  { tuxTroutingEntry 1 }

tuxTroutingBufType   OBJECT-TYPE
     SYNTAX  DisplayString (SIZE(1..256))
     ACCESS  read-write -- writable only during row creation
     STATUS  mandatory
     DESCRIPTION
               " List  of  types  and subtypes of data buffers for which
                 this  routing  entry  is  valid.   A  maximum   of   32
                 type/subtype  combinations  are allowed.  The types are
                 restricted  to  be  one  of  FML,  VIEW,  X_C_TYPE,  or
                 X_COMMON.   No  subtype  can be specified for type FML,
                 and subtypes are required for types VIEW, X_C_TYPE, and
                 X_COMMON  (``*''  is  not  allowed).  Note that subtype
                 names should not contain semicolon,  colon,  comma,  or
                 asterisk  characters.  Duplicate type/subtype pairs can
                 not be specified for the same routing  criterion  name;
                 more than one routing entry can have the same criterion
                 name as long as the type/subtype pairs are unique.   If
                 multiple  buffer types are specified for a single rout-
                 ing entry, the data types of the routing field for each
                 buffer type must be the same.
      NOTE:
	     1. This object is applicable only for service based routing.
             2. This object can be set only during row creation."
     ::=  { tuxTroutingEntry 2 }

tuxTroutingField   OBJECT-TYPE
     SYNTAX  DisplayString (SIZE(1..30))
     ACCESS  read-write
     STATUS  mandatory
     DESCRIPTION
   " Routing field name.

     For Service Based Routing: (ATMI or CORBA C++ Interface)

     This field is assumed to be an FML buffer or view field name 
     that is identified in an FML field table (using the FLDTBLDIR and FIELDTBLS
     environment variables) or an FML view table (using the VIEWDIR and 
     VIEWFILES environment variables), respectively. This information is used 
     to get the associated field value for data dependent routing during the 
     sending of a message.

     For Factory Based Routing: (CORBA C++ Interface only)

     This is assumed to be a field that is specified in an NVList parameter to 
     PortableServer::POA::create_reference_with_criteria for an interface that 
     has this factory routing criteria associated with it. See CORBA C++ 
	 Interface documentation for more details."
     ::=  { tuxTroutingEntry 3 }

tuxTroutingRanges   OBJECT-TYPE
     SYNTAX  DisplayString (SIZE(1..1024))
     ACCESS  read-write
     STATUS  mandatory
     DESCRIPTION
   " The ranges and associated server groups for this routing criteria. 
          criteria: range: group.
          range: value | lower - upper | *
          lower: value
          upper: value
          value: MIN | MAX | numeric | `string' 
          group: string | *
          numeric: [+ | -]digits[.digits][e | E[ | +
          | - ] digit
          digit: 0-9
          digits: digit[digit] 

     \ can be used to escape the single-quote character in strings.
     Lower must be less than upper.
     Group specified as a string must specify a valid tuxTgroupName.

     Limitation: Attribute values greater than 256 bytes  in
     length   will   disable  interoperability  with  TUXEDO
     System/T Release 4.2.2 and earlier. "
     ::=  { tuxTroutingEntry 4 }


tuxTroutingState   OBJECT-TYPE
     SYNTAX  INTEGER {
                valid(1),
		invalid(3),
                unknown(2)
                }
     ACCESS  read-write
     STATUS  mandatory
     DESCRIPTION
               "GET:
               A  GET  operation  will   retrieve   configuration
               information  for the selected tuxTroutingTable row(s).
               The following states indicate  the  meaning  of  a
               tuxTroutingState returned  in  response to a GET request.
               States not listed will not be returned.

               valid(1)     tuxTroutingTable instance is defined. Note
                            that this is the only valid state for
                            this  class.   Routing  criteria  are
                            never  active; rather, they are asso-
                            ciated through the configuration with
                            service  names  and are acted upon at
                            runtime  to  provide  data  dependent
                            routing.

               SET:
               A SET operation will update configuration informa-
               tion  for the selected tuxTroutingTable instance. The fol-
               lowing states indicate the meaning of a tuxTroutingState
               set  in  a SET request.  States not listed may not
               be set.

               invalid(3)   Delete tuxTroutingTable instance for applica-
                            tion.  State change allowed only when
                            in  the  valid(1) state. Successful return
                            removes the instance from the table."

     ::=  { tuxTroutingEntry 5 }

beaRoutingType OBJECT-TYPE
        SYNTAX  INTEGER {
                service(1),
                factory(2)
        }
	ACCESS read-write
        STATUS mandatory
        DESCRIPTION
      " factory(2) specifies that the routing criteria applies to factory-based 	
	routing for a CORBA interface. service(1) specifies that the routing 
	criteria applies to data-dependent routing for a BEA TUXEDO service.
        Note that the type affects the validity and possible values for other 
	fields defined for this table class. These are noted in the description 
	for tuxTroutingEntry. 
	NOTE: This object can be SET during row creation only."
        ::= { tuxTroutingEntry 6 }

tuxRoutingFieldType OBJECT-TYPE
        SYNTAX  INTEGER {
                short(1),
                long(2),
		float(3),
		double(4),
		char(5),
		string(6)
        }
	ACCESS read-write
        STATUS mandatory
        DESCRIPTION
      " Valid only for Factory based routing. (CORBA C++ Interface only)
	This specifies the type of tuxTroutingField on which this routing 
	criteria is defined.
	NOTE: 
	1. This object can be set only during row creation. 
	2. This object is applicable only for Factory Based routing criteria."
        ::= { tuxTroutingEntry 7 }
 
tuxInternalIdx OBJECT-TYPE
        SYNTAX  DisplayString (SIZE(1..30))
	ACCESS read-write
        STATUS mandatory
        DESCRIPTION
      " tuxInternalIdx is used as an index instead of tuxTroutingBufType/
	tuxTroutingField (for service/factory based routing respectively)
 	to reduce the size of the index.

   	For Factory Based Routing: 
		 o tuxInternalIdx should always be equal to tuxTroutingField

 	For Service Based Routing: 
		 o tuxInternalIdx should always equal the first 30 characters
		   in tuxTroutingBufType.
	NOTE: This object can be SET only during row creation"
        ::= { tuxTroutingEntry 8 }

--*****************************************************************************
-- The tuxTulog group represents runtime attributes of userlog(3)
-- files within an application.
--*****************************************************************************

tuxTulogTable OBJECT-TYPE
	SYNTAX	SEQUENCE OF TuxTulogEntry
	ACCESS	not-accessible
	STATUS	mandatory
	DESCRIPTION 
		  " This table contains information on userlog messages for
		    the local machine."
	::= { tuxTulog 1 }

tuxTulogEntry OBJECT-TYPE
	SYNTAX TuxTulogEntry
	ACCESS  not-accessible
	STATUS  mandatory
        DESCRIPTION
		  " A row in tuxTulogTable . 
   		    Associated with this group is a control MIB group, 
		    tuxTulogCtrl which controls the values returned for 
		    tuxTulog. "
	INDEX { tuxTulogSerNo }
	::= { tuxTulogTable 1 }

TuxTulogEntry ::= SEQUENCE {
   tuxTulogSerNo
	INTEGER,
   tuxTulogLmid
	DisplayString,
   tuxTulogPmid
	DisplayString,
   tuxTulogMmDdDYy
	INTEGER,
   tuxTulogTime
	INTEGER,
   tuxTulogLine
	INTEGER,
   tuxTulogMsg
	DisplayString,
   tuxTulogTpTranId
	DisplayString,
   tuxTulogXid
	DisplayString,
   tuxTulogPid
	INTEGER,
   tuxTulogSeverity
	DisplayString,
   tuxTulogCat
	DisplayString,
   tuxTulogMsgNum
	INTEGER,
   tuxTulogProcName
	DisplayString,
   tuxTulogThreadID
	INTEGER,
   tuxTulogContextID
	INTEGER
   }

tuxTulogSerNo   OBJECT-TYPE
     SYNTAX  INTEGER 
     ACCESS  read-only
     STATUS  mandatory
     DESCRIPTION
               "A running serial number for the rows in tuxTulogTable. " 
     ::=  { tuxTulogEntry 1 }
 
tuxTulogLmid   OBJECT-TYPE
     SYNTAX  DisplayString (SIZE(1..30))
     ACCESS  read-only
     STATUS  mandatory
     DESCRIPTION
               " Retrieval machine logical machine identifier. "
     ::=  { tuxTulogEntry 2 }

tuxTulogPmid   OBJECT-TYPE   
     SYNTAX  DisplayString (SIZE(1..30))       
     ACCESS  read-only
     STATUS  mandatory 
     DESCRIPTION       
               "  Physical machine identifier. " 
     ::=  { tuxTulogEntry 3 }       
 
tuxTulogMmDdDYy   OBJECT-TYPE   
     SYNTAX  INTEGER 
     ACCESS  read-only
     STATUS  mandatory 
     DESCRIPTION       
               " monthdateyear  of the log file." 
     ::=  { tuxTulogEntry 4 }       
 
tuxTulogTime   OBJECT-TYPE   
     SYNTAX  INTEGER 
     ACCESS  read-only
     STATUS  mandatory 
     DESCRIPTION       
               " Time at which the message was generated. " 
     ::=  { tuxTulogEntry 5 }       
 
tuxTulogLine   OBJECT-TYPE   
     SYNTAX  INTEGER 
     ACCESS  read-only
     STATUS  mandatory 
     DESCRIPTION       
               " Line number of the message in the log file " 
     ::=  { tuxTulogEntry 6 }       
 
tuxTulogMsg   OBJECT-TYPE   
     SYNTAX  DisplayString (SIZE(1..256))       
     ACCESS  read-only
     STATUS  mandatory 
     DESCRIPTION       
               " The entire text of the userlog message as it appears in
          	 the userlog file."
     ::=  { tuxTulogEntry 7 }       
 
tuxTulogTpTranId   OBJECT-TYPE   
     SYNTAX  DisplayString (SIZE(1..78))       
     ACCESS  read-only
     STATUS  mandatory 
     DESCRIPTION       
               " Transaction identifier as returned  from  tpsuspend(3).
          	 The  data  in  this  field  should  not  be interpreted
          	 directly by the user except  for  equality  comparison.
          	 Messages not associated with transactions will retrieve
          	 a 0-length string as the value for this attribute. "
     ::=  { tuxTulogEntry 8 }       
 
tuxTulogXid   OBJECT-TYPE   
     SYNTAX  DisplayString (SIZE(1..78))       
     ACCESS  read-only
     STATUS  mandatory 
     DESCRIPTION       
               " Transaction identifier  as  returned  from  tx_info(3).
          	 The  data  in  this  field  should  not  be interpreted
          	 directly by the user except  for  equality  comparison.
          	 Messages not associated with transactions will retrieve
          	 a 0-length string as the value for this attribute. "
     ::=  { tuxTulogEntry 9 }       
 
tuxTulogPid   OBJECT-TYPE   
     SYNTAX  INTEGER 
     ACCESS  read-only
     STATUS  mandatory 
     DESCRIPTION       
               " Process identifier of the client or  server  that  gen-
          	 erated the userlog message. "
     ::=  { tuxTulogEntry 10 }       
 
tuxTulogSeverity   OBJECT-TYPE   
     SYNTAX  DisplayString (SIZE(1..30))       
     ACCESS  read-only
     STATUS  mandatory 
     DESCRIPTION       
               " Severity of message, if any. "
     ::=  { tuxTulogEntry 11 }       
 
tuxTulogCat   OBJECT-TYPE   
     SYNTAX  DisplayString (SIZE(1..30))       
     ACCESS  read-only
     STATUS  mandatory 
     DESCRIPTION       
               " Catalog name from which the  message  was  derived,  if
          	 any. " 
     ::=  { tuxTulogEntry 12 }       
 
tuxTulogMsgNum   OBJECT-TYPE   
     SYNTAX  INTEGER
     ACCESS  read-only
     STATUS  mandatory 
     DESCRIPTION       
               " Catalog message number, if the message was derived from
          	 a catalog. " 
     ::=  { tuxTulogEntry 13 }       
 
tuxTulogProcName   OBJECT-TYPE   
     SYNTAX  DisplayString (SIZE(1..30))       
     ACCESS  read-only
     STATUS  mandatory 
     DESCRIPTION       
               " Process name of the client or server that generated the
          	 userlog message. " 
     ::=  { tuxTulogEntry 14 }       
 
-- Added : BEGIN-JANUS-NS-TUXEDO7.1-041400

tuxTulogThreadID   OBJECT-TYPE   
     SYNTAX  INTEGER
     ACCESS  read-only
     STATUS  mandatory 
     DESCRIPTION       
	 "Identifier for the thread that wrote this userlog message. 
          	 Support : Tuxedo 7.1 and later. " 
     ::=  { tuxTulogEntry 20 }       
 
tuxTulogContextID   OBJECT-TYPE   
     SYNTAX  INTEGER (-2..29999)
     ACCESS  read-only
     STATUS  mandatory 
     DESCRIPTION       
	"Identifier for this particular application association.
          	 Support : Tuxedo 7.1 and later. " 
     ::=  { tuxTulogEntry 30 }       

-- Added : END-JANUS-NS-TUXEDO7.1-041400
 
-- *********************************************************************
-- tuxTulogCtrl -  control MIB for tuxTulogTable
-- The values of objects in this group control the ulog messages returned
-- by the tuxTulogTable.
-- *********************************************************************

tuxTulogCtrl	OBJECT IDENTIFIER ::= { tuxTulog 2 }

tuxTulogLmidCtrl OBJECT-TYPE	
     SYNTAX  DisplayString (SIZE(1..30))
     ACCESS  read-write
     STATUS  mandatory
     DESCRIPTION
               " Logical machine id to qualify machine from where the userlog 
		 file is read for tuxTulogTable. By default, the ULOG messages 
		 from files on the local host are returned, per the ULOGPFX. 
		 To go back to the default setting, set this object to `null'. 
		 "
     ::=  { tuxTulogCtrl 1 }

tuxTulogPmidCtrl OBJECT-TYPE
     SYNTAX  DisplayString (SIZE(1..30))
     ACCESS  read-write
     STATUS  mandatory
     DESCRIPTION
               " Physical machine name to qualify the source machine for userlog
		 messages to be listed in tuxTulogTable. By default messages 
		 from all hosts within ULOG files qualified by tuxTulogLmidCtrl
		 are returned. To go back to the default setting, set this 
		 object to `null'. "
     ::=  { tuxTulogCtrl 2 }

tuxTulogMmddyyCtrl OBJECT-TYPE
     SYNTAX  INTEGER
     ACCESS  read-write
     STATUS  mandatory
     DESCRIPTION
               " Date value to qualify userlog messages to be listed in 
	         tuxTulogTable. e.g. for April 6th 1988 use 40688.
		 By default messages for the current date are returned.
		 To go back to the default setting, set this object to 0." 
     ::=  { tuxTulogCtrl 3 }

tuxTulogTimeCtrl OBJECT-TYPE
     SYNTAX  INTEGER
     ACCESS  read-write
     STATUS  mandatory
     DESCRIPTION
               " Starting time for the time range for which the userlog 
		 messages are to be listed in tuxTulogTable. This number 
		 is calculated as under - `hrs*10000 + mins*100 + secs'. 
		 The default value is 0."
     ::=  { tuxTulogCtrl 4 }

tuxTulogEndTimeCtrl OBJECT-TYPE
     SYNTAX  INTEGER
     ACCESS  read-write
     STATUS  mandatory
     DESCRIPTION
               " Ending time for the time range for which the userlog 
		 messages are to be listed in tuxTulogTable. This number 
		 is calculated as under - `hrs*10000 + mins*100 + secs'. 
		 By default the maximum  value is considered. To revert to
		 the default setting, set this object to 0."
     ::=  { tuxTulogCtrl 5 }

tuxTulogLineCtrl OBJECT-TYPE
     SYNTAX  INTEGER
     ACCESS  read-write
     STATUS  mandatory
     DESCRIPTION
               " Beginning line number from which the userlog messages are 
		 to be listed in tuxTulogTable. By default all messages are
		 returned. To revert to the default setting , set this object 
		 to 0."
     ::=  { tuxTulogCtrl 6 }

tuxTulogMsgCtrl OBJECT-TYPE
     SYNTAX  DisplayString (SIZE(1..30))
     ACCESS  read-write
     STATUS  mandatory
     DESCRIPTION
               " Regular Expression to qualify userlog messages to be listed
                 in tuxTulogTable on the basis of the message body. By default
		 messsages with any body are listed. To revert to the default 
		 setting, set this object to `null'. "
     ::=  { tuxTulogCtrl 7 }

tuxTulogTptranIdCtrl OBJECT-TYPE
     SYNTAX  DisplayString (SIZE(1..78))
     ACCESS  read-write
     STATUS  mandatory
     DESCRIPTION
               " Value of tuxTulogTpTranId to qualify messages to be displayed 
		 in the in tuxTulogTable. By default all messages are returned. 
		 To revert to this default setting set this  object to `null'."
     ::=  { tuxTulogCtrl 8 }

tuxTulogXidCtrl OBJECT-TYPE
     SYNTAX  DisplayString (SIZE(1..30))
     ACCESS  read-write
     STATUS  mandatory
     DESCRIPTION
               " Value of tuxTulogXid to qualify messages to be displayed in the
                 in tuxTulogTable. By default all messages are returned. 
		 To revert to this default setting, set this object to 
		 `null'. "
     ::=  { tuxTulogCtrl 9 }

tuxTulogPidCtrl OBJECT-TYPE
     SYNTAX  INTEGER
     ACCESS  read-write
     STATUS  mandatory
     DESCRIPTION
               " Value of Process Id of the source to qualify messages to be 
		 displayed in the in tuxTulogTable. By default messages with
		 any pid are listed. To revert to this default setting, set 
		 this object to 0 . "
     ::=  { tuxTulogCtrl 10 }

tuxTulogSeverityCtrl OBJECT-TYPE    
     SYNTAX  DisplayString (SIZE(1..30)) 
     ACCESS  read-write
     STATUS  mandatory   
     DESCRIPTION 
               " Regular Expression to qualify userlog messages to be listed 
                 in tuxTulogTable on the basis of message severity, if any.
		 By default, messages with any severity are listed. To revert 
		 to this default setting, set this object to `null'. "
     ::=  { tuxTulogCtrl 11 } 
 
tuxTulogCatCtrl OBJECT-TYPE    
     SYNTAX  DisplayString (SIZE(1..30)) 
     ACCESS  read-write
     STATUS  mandatory   
     DESCRIPTION 
               " Regular Expression to qualify userlog messages to be listed 
                 in tuxTulogTable on the basis of the catalog name, if any . 
		 By default messages from all catalogs are listed. To revert 
		 to this default setting, set this object to `null'. "
     ::=  { tuxTulogCtrl 12 } 
 
tuxTulogMsgNumCtrl OBJECT-TYPE    
     SYNTAX  INTEGER 
     ACCESS  read-write
     STATUS  mandatory   
     DESCRIPTION 
               " Message number in catalog to qualify userlog messages to be 
		 listed in tuxTulogTable. By default all message numbers are
		 returned.
		 To revert to this default setting, set this object to 0. "
     ::=  { tuxTulogCtrl 13 } 

tuxTulogProcNameCtrl OBJECT-TYPE    
     SYNTAX  DisplayString (SIZE(1..30)) 
     ACCESS  read-write
     STATUS  mandatory   
     DESCRIPTION 
               " Regular Expression to qualify userlog messages to be listed 
                 in tuxTulogTable on the basis of the process name which gener-
		 ated the message, if known. By default, messages with all 
		 process names are returned. To revert to this default setting,
		 set this object to `null'. "
     ::=  { tuxTulogCtrl 14 } 

--******************************************************************************
-- ACL MIB
-- This MIB defines a set of groups through which the /T Access Control Lists 
-- can be managed.
--******************************************************************************


--******************************************************************************
-- tuxTAclGrp 
-- The tuxTAclGrp group represents groups of TUXEDO application
-- users and domains.
--******************************************************************************

tuxTAclGrp	OBJECT IDENTIFIER ::=	{ tuxTAcl 1 }

tuxTAclGrpTable OBJECT-TYPE
        SYNTAX  SEQUENCE OF TuxTAclGrpEntry
        ACCESS  not-accessible
        STATUS  mandatory
        DESCRIPTION
                  " This table contains information on groups of TUXEDO applica-
		    tions users and domains. "
        ::= { tuxTAclGrp 1 }
 
tuxTAclGrpEntry OBJECT-TYPE
        SYNTAX TuxTAclGrpEntry
        ACCESS  not-accessible
        STATUS  mandatory
        DESCRIPTION
                  " A row in tuxTAclGrpTable .
		Creation of a new group ( instance ):
		===================================
		A set request for a non-existing instance is required. "
        INDEX { tuxTAclGrpName }
        ::= { tuxTAclGrpTable 1 }
 
TuxTAclGrpEntry ::= SEQUENCE {
   tuxTAclGrpName
        DisplayString,
   tuxTAclGrpId
        INTEGER,
   tuxTAclGrpState
        INTEGER
   }

tuxTAclGrpName OBJECT-TYPE
        SYNTAX DisplayString (SIZE(1..30))
        ACCESS read-write	-- writable only during row creation	
        STATUS  mandatory    
        DESCRIPTION 
                  " Logical name of the group.  A group name is a string of
          	    printable  characters  and cannot contain a pound sign,
          	    comma, colon, or newline.  
		Note: This object can be set only during row creation."
        ::= { tuxTAclGrpEntry 1 }
 
tuxTAclGrpId OBJECT-TYPE
        SYNTAX INTEGER (0..16384) 
        ACCESS read-write
        STATUS  mandatory     
        DESCRIPTION  
                  "  Group identifier associated with this user.  A value of
          	     0  indicates  the default group `other'.  If not speci-
          	     fied at creation time, it defaults to the  next  avail-
          	     able (unique) identifier greater than 0. "
        ::= { tuxTAclGrpEntry 2 } 
  
tuxTAclGrpState OBJECT-TYPE
        SYNTAX INTEGER {
		valid(1),
		invalid(2)
	}
        ACCESS read-write               -- rw
        STATUS  mandatory     
        DESCRIPTION  
                  " GET:
               A GET operation will retrieve configuration infor-
               mation for the selected tuxTAclGrpTable instance(s). The
               following  states  indicate  the  meaning   of   a
               tuxTAclGrpState returned in response to a GET request.
               States not listed will not be returned.

               valid(1)  tuxTAclGrpTable instance is defined  and  inac-
                         tive.   Note that this is the only valid
                         state for this class.   ACL  groups  are
                         never active.

          SET: 
               A SET operation will update configuration informa-
               tion for the selected tuxTAclGrpTable instance. The fol-
               lowing states indicate the meaning of a tuxTAclGrpState
               set  in  a SET request.  States not listed may not be set.

               invalid(2)
			 Delete tuxTAclGrpTable instance for  applica-
                         tion. Successful return removes the instance
			 from the table. " 
        ::= { tuxTAclGrpEntry 3 } 
  
--******************************************************************************
-- tuxTAclPerm 
-- The tuxTAclPerm group indicates what  groups  are  allowed  to
-- access TUXEDO System entities.  These entities are named via
-- a string.  The  names  currently  represent  service  names,
-- event names, and application queue names.
--******************************************************************************
 
tuxTAclPerm      OBJECT IDENTIFIER ::=   { tuxTAcl 2 }
 
tuxTAclPermTable OBJECT-TYPE
        SYNTAX  SEQUENCE OF TuxTAclPermEntry
        ACCESS  not-accessible
        STATUS  mandatory
        DESCRIPTION
                  " This table contains information on access priveleges of 
		    server groups on Tuxedo entities."
        ::= { tuxTAclPerm 1 }
 
tuxTAclPermEntry OBJECT-TYPE
        SYNTAX TuxTAclPermEntry
        ACCESS  not-accessible
        STATUS  mandatory
        DESCRIPTION
                  " A row in tuxTAclPermTable .
		Creation of a new group ( instance ):
		===================================
		A set request for a non-existing instance with atleast tuxT-
		AclPermName and tuxTAclPermType is required. "
        INDEX { tuxTAclPermName, tuxTAclPermType }
        ::= { tuxTAclPermTable 1 }
 
TuxTAclPermEntry ::= SEQUENCE {
   tuxTAclPermName
        DisplayString,
   tuxTAclPermType
        INTEGER,
   tuxTAclPermGrpIds
        DisplayString,
   tuxTAclPermState
	INTEGER
   }

tuxTAclPermName OBJECT-TYPE
        SYNTAX  DisplayString (SIZE(1..30))
        ACCESS  read-write	-- writable only during row creation
        STATUS  mandatory    
        DESCRIPTION
                  " The name of the entity for which permissions are  being
          	    granted.   The  name  can  represent a service name, an
          	    event name, and/or a queue name.   An  ACL  name  is  a
          	    string  of  printable  characters  and cannot contain a
          	    colon, pound sign, or newline.  
		Note: This object can be set only during row creation."
        ::= { tuxTAclPermEntry 1 }
 
tuxTAclPermType OBJECT-TYPE
        SYNTAX  INTEGER {
		enq(1),
		deq(2),
		service(3),
		postevent(4)
	} 
        ACCESS  read-write	-- writable only during row creation
        STATUS  mandatory     
        DESCRIPTION 
                  " The type of the entity for which permissions are  being
          	    granted.  
		Note: This object can be set only during row creation."
        ::= { tuxTAclPermEntry 2 } 

tuxTAclPermGrpIds OBJECT-TYPE
        SYNTAX  DisplayString  (SIZE(0..800))
        ACCESS  read-write
        STATUS  mandatory
        DESCRIPTION
                  " A comma separated list of group  identifiers  (numbers)
          	    that  are  permitted  access  to the associated entity.
          	    The length of string is limited only by the  amount  of
          	    disk space on the machine. "
        ::= { tuxTAclPermEntry 3 }
 
tuxTAclPermState OBJECT-TYPE
        SYNTAX  INTEGER {
		valid(1),
		invalid(2)
		} 
        ACCESS  read-write
        STATUS  mandatory     
        DESCRIPTION 
                  "
          GET:
               A GET operation will retrieve configuration infor-
               mation  for all selected entities .  The following  
	       states  indicate  the  meaning   of   a
               tuxTAclPermState  returned  in  response to a GET 
	       request. States not listed will not be returned.

               valid(1)  tuxTAclPerm instance is  defined .
                         Note that this is the only valid
                         state for this class.   ACL  permissions
                         are never active.

          SET: 
               A SET operation will update configuration informa-
               tion  for the selected tuxTAclPerm instance.  The fol-
               lowing states indicate the meaning of  a  tuxTAcl-
	       PermState set in a SET request.  States not listed 
	       may not be set.


               invalid(2) Delete tuxTAclPerm instance for application.
                         State  change  allowed  only when in the
                         valid(1) state.  Successful  return  leaves
                         the object in the invalid(2) state.

	  Note that the tuxTAclPerm instance refers to all groupids 
	  related to a particular tuxTAclPermName in the Table. "
        ::= { tuxTAclPermEntry 4 } 
  
--************************************************************************** 
--   The tuxTAclPrincipal group represents users  or  domains  that
--   can  access  a  TUXEDO  application and the group with which
--   they are associated.  To join the application as a  specific
--   user, it is necessary to present a user-specific password.
--************************************************************************** 

tuxTAclPrincipal      OBJECT IDENTIFIER ::=   { tuxTAcl 3 }

tuxTAclPrinTbl OBJECT-TYPE
        SYNTAX  SEQUENCE OF TuxTAclPrinEntry
        ACCESS  not-accessible
        STATUS  mandatory
        DESCRIPTION
                  " This table contains  users  or  domains  that can  access  
	 	    a  TUXEDO  application and the group with which they are 
		    associated. "
        ::= { tuxTAclPrincipal 1 }

tuxTAclPrinEntry OBJECT-TYPE
        SYNTAX TuxTAclPrinEntry
        ACCESS  not-accessible
        STATUS  mandatory
        DESCRIPTION
                  " A row in tuxTAclPrinTbl. 
		Creation of a new group ( instance ):
		===================================
		A set request for a non-existing instance is required. "
        INDEX { tuxTAclPrinName }
        ::= { tuxTAclPrinTbl 1 }

TuxTAclPrinEntry ::= SEQUENCE {
   tuxTAclPrinName
        DisplayString,
   tuxTAclCltName
        DisplayString,
   tuxTAclPrinId
        INTEGER,
   tuxTAclPrinGrp
        INTEGER,
   tuxTAclPrinPasswd
	DisplayString,
   tuxTAclPrinState
	INTEGER
   }
 
tuxTAclPrinName OBJECT-TYPE
        SYNTAX  DisplayString (SIZE(1..30))
        ACCESS  read-write	-- writable only during row creation
        STATUS  mandatory
        DESCRIPTION
                  " Logical name of the user or domain  (a  principal).   A
          	    principal  name is a string of printable characters and
          	    cannot contain a pound sign, colon, or newline. 
		Note: This object can be set only during row creation."
	::= { tuxTAclPrinEntry 1 }

tuxTAclCltName OBJECT-TYPE
        SYNTAX  DisplayString (SIZE(1..30))
        ACCESS  read-write              -- rw
        STATUS  mandatory
        DESCRIPTION
                  " The client name associated with the user.  It generally
          	    describes the role of the associated user, and provides
          	    a further qualifier on the user entry.  If  not  speci-
          	    fied  at  creation  time,  the  default is the wildcard
          	    asterisk (*).  A client name is a string  of  printable
          	    characters and cannot contain a colon, or newline. "
        ::= { tuxTAclPrinEntry 2 } 
 
tuxTAclPrinId OBJECT-TYPE
        SYNTAX  INTEGER (1..131072) 
        ACCESS  read-write	-- writable only during row creation
        STATUS  mandatory
        DESCRIPTION
                  " Unique user identification number.  If not specified at
          	    creation  time,  it  defaults  to  the  next  available
          	    (unique) identifier greater than 0. 
		Note: This object can be set only during row creation."
        ::= { tuxTAclPrinEntry 3 } 
 
tuxTAclPrinGrp OBJECT-TYPE
        SYNTAX  INTEGER (0..16384)
        ACCESS  read-write
        STATUS  mandatory
        DESCRIPTION
                  " Group identifier associated with this user.  A value of
          	    0  indicates  the default group `other'.  If not speci-
          	    fied at creation time, the default value 0 is assigned. "
        ::= { tuxTAclPrinEntry 4 } 
 
tuxTAclPrinPasswd OBJECT-TYPE
        SYNTAX  DisplayString
        ACCESS  read-write	-- the value of this object cannot be read
        STATUS  mandatory
        DESCRIPTION
                  " The clear-text authentication password for the  associ-
          	   ated  user.   Note  that  the system will automatically
          	   encrypt this information on behalf of  the  administra-
          	   tor. "
        ::= { tuxTAclPrinEntry 5 } 
 
tuxTAclPrinState OBJECT-TYPE
        SYNTAX  INTEGER {
		valid(1),
		invalid(2)
		} 
        ACCESS  read-write
        STATUS  mandatory
        DESCRIPTION
             " A GET operation will retrieve configuration infor-
               mation  for the selected tuxTAclPrinTbl instance(s).
               The following states indicate  the  meaning  of  
               tuxTAclPrinState  :

               valid(1)  tuxTAclPrinTbl  instance  is  defined  and
                         inactive.   Note  that  this is the only
                         valid state for this class.  ACL princi-
                         pals are never active.

          SET: 
               A SET operation will update configuration informa-
               tion  for the selected tuxTAclPrinTbl instance. The
               following  states  indicate  the  meaning   of   a
               tuxTAclPrinState set in a SET request.  States not 
	       listed may not be set.

              invalid(2) Delete tuxTAclPrinTbl instance for  appli-
                         cation.   State change allowed only when
                         in the valid(1) state.   Successful  return
                         leaves the object in the invalid(2) state. "
        ::= { tuxTAclPrinEntry 6 } 

--*************************************************************************** 
-- tuxTAppQctrl group
-- This is a control MIB to enable controlled access to all MIB groups which
-- are a part of tuxTAppQ.
--*************************************************************************** 

tuxTAppQctrl	OBJECT IDENTIFIER ::=	{ tuxTAppQ 5 }

 tuxTAppQctrlLmid OBJECT-TYPE
        SYNTAX  INTEGER {
		local(1),
		all(2)
		} 
        ACCESS  read-write
        STATUS  mandatory
        DESCRIPTION
                  " This applies to all MIB groups in tuxTAppQ. The value of 
		    this object controls the machines for which the values are 
		    returned.

		    If the value is local(1) only the local host where the
		    SNMP agent is running, is considered or else all known
		    LMIDs to the application are considered if the value is
		    all(2).

		    The default value of this object is `local'. " 
        ::= { tuxTAppQctrl 1 }

 tuxTAppQctrlQmConfig OBJECT-TYPE 
        SYNTAX  DisplayString (SIZE(1..256)) 
        ACCESS  read-write 
        STATUS  mandatory 
        DESCRIPTION  
                  " This applies to all MIB groups in tuxTAppQ. The value of 
		    this object controls the device for which the values are 
		    returned. 

                    The default value of this object is `*', in which case
		    all known (which are a part of some group) devices are 
		    considered. "
        ::= { tuxTAppQctrl 2 } 
 
 tuxTAppQctrlSpaceName OBJECT-TYPE 
        SYNTAX  DisplayString (SIZE(1..15)) 
        ACCESS  read-write 
        STATUS  mandatory 
        DESCRIPTION  
                  " This applies to all MIB groups in tuxTAppQ. The value of 
		    this object controls the queue space for which the values 
		    are returned.
 
                    The default value of this object is `*', in which case
                    all queue spaces for the  devices (qualified by 
		    tuxTAppQctrlQmConfig) are considered. "
        ::= { tuxTAppQctrl 3 } 
 
 tuxTAppQctrlQname OBJECT-TYPE  
        SYNTAX  DisplayString (SIZE(1..15)) 
        ACCESS  read-write  
        STATUS  mandatory  
        DESCRIPTION      
                  " The value of this object controls the queue for 
                    which the values are returned. This applies to tuxTAppQTbl,
		    and tuxTAppQmsgTbl.
 
                    The default value of this object is `*', in which case
                    all queues for the  devices (qualified by 
                    tuxTAppQctrlQmConfig) and queue spaces (qualified by tuxT-
		    AppQctrlSpaceName) are considered. "
        ::= { tuxTAppQctrl 4 } 

tuxTAppQctrlMsgLoPrio OBJECT-TYPE
        SYNTAX INTEGER
        ACCESS  read-write
        STATUS  mandatory
        DESCRIPTION
                  " This object applies only to tuxTAppQmsgTbl. The lowest 
	            priority within which to  search for occurrences of 
		    tuxTAppQmsgTbl instances. This is valid only for PRIO-based 
		    queues. By default the minimum value of priority is consi-
		    dered. To use the default setting, set this object to 0." 
        ::= { tuxTAppQctrl 5 }

tuxTAppQctrlMsgHiPrio OBJECT-TYPE
        SYNTAX  INTEGER
        ACCESS  read-write
        STATUS  mandatory
        DESCRIPTION
                  " This object applies only to tuxTAppQmsgTbl. The highest 
		    priority within which to  search for occurrences of 
		    tuxTAppQmsgTbl instances. This is valid only for PRIO-based 
		    queues. By default the maximum value of priority consi-
		    dered. To use the default setting, set this object to 0."
        ::= { tuxTAppQctrl 6 }

tuxTAppQctrlMsgEndTime OBJECT-TYPE
	SYNTAX  DisplayString (SIZE(1..12))
	ACCESS  read-write
	STATUS  mandatory
	DESCRIPTION
		   " This object applies only to tuxTAppQmsgTbl. The end  time  
		     within  which to search for occurrences of tuxTAppQmsgTbl 
		     instances. The range is inclusive. This is valid only for
		     TIME based queues.
		     Format YY[MM[DD[hh[mm[ss]]]]] - specifies the year, month
		     date, hour, minute and seconds respectively. Any value
		     which is not specified defaults to it's minimum value e.g.
		     9506 is taken as 950601000000. The years 00 thru 37 are
		     treated as 2000 thru 2037, 70 through 99 as 1970 through
		     1999 and 38 through 69 are invalid. By default the maxim-
		     um value of time is considered. To use the default setting 
		     set this object to `*' ."
        ::= { tuxTAppQctrl 7 }
 
tuxTAppQctrlMsgStartTime	OBJECT-TYPE
        SYNTAX  DisplayString (SIZE(1..12))
        ACCESS  read-write
        STATUS  mandatory
        DESCRIPTION
                   " This object applies only to tuxTAppQmsgTbl. The start time
		     within  which  to search for occurrences of tuxTAppQmsgTbl 
	    	     instances. The range is inclusive. 
	   	     the format. This is valid only for TIME-based queues. 
		     Format YY[MM[DD[hh[mm[ss]]]]] - specifies the year, month
		     date, hour, minute and seconds respectively. Any value
		     which is not specified defaults to it's minimum value e.g.
		     9506 is taken as 950601000000. The years 00 thru 37 are
		     treated as 2000 thru 2037, 70 through 99 as 1970 through
		     1999 and 38 through 69 are invalid. By default the minimum 
                     value of time is considered. To use the default setting 
		     set this object to `*' ." 
        ::= { tuxTAppQctrl 8 }
 
-- Added : BEGIN-JANUS-NS-TUXEDO7.1-041400

tuxTAppQctrlMsgExpireEndTime OBJECT-TYPE
	SYNTAX  DisplayString (SIZE(1..12))
	ACCESS  read-write
	STATUS  mandatory
	DESCRIPTION
		   " This object applies only to tuxTAppQmsgTbl. The Expire end  time  
		     within  which to search for occurrences of tuxTAppQmsgTbl 
		     instances. The range is inclusive. This is valid only for
		     TIME based queues.
		     Format YY[MM[DD[hh[mm[ss]]]]] - specifies the year, month
		     date, hour, minute and seconds respectively. Any value
		     which is not specified defaults to it's minimum value e.g.
		     9506 is taken as 950601000000. The years 00 thru 37 are
		     treated as 2000 thru 2037, 70 through 99 as 1970 through
		     1999 and 38 through 69 are invalid. By default the maxim-
		     um value of time is considered. To use the default setting 
		     set this object to `*' .
		 	Support: Tuxedo 7.1 and later"
        ::= { tuxTAppQctrl 20 }
 
tuxTAppQctrlMsgExpireStartTime	OBJECT-TYPE
        SYNTAX  DisplayString (SIZE(1..12))
        ACCESS  read-write
        STATUS  mandatory
        DESCRIPTION
                   " This object applies only to tuxTAppQmsgTbl. The Expire start time
		     within  which  to search for occurrences of tuxTAppQmsgTbl 
	    	     instances. The range is inclusive. 
	   	     the format. This is valid only for TIME-based queues. 
		     Format YY[MM[DD[hh[mm[ss]]]]] - specifies the year, month
		     date, hour, minute and seconds respectively. Any value
		     which is not specified defaults to it's minimum value e.g.
		     9506 is taken as 950601000000. The years 00 thru 37 are
		     treated as 2000 thru 2037, 70 through 99 as 1970 through
		     1999 and 38 through 69 are invalid. By default the minimum 
                     value of time is considered. To use the default setting 
		     set this object to `*' .
		 	Support: Tuxedo 7.1 and later"
        ::= { tuxTAppQctrl 30 }
 
-- Added : END-JANUS-NS-TUXEDO7.1-041400

--*************************************************************************** 
-- The tuxTAppQ group represents application queues.  One or more
-- application  queues  may exist in a single application queue
-- space.
--*************************************************************************** 

tuxTAppQTbl OBJECT-TYPE
        SYNTAX  SEQUENCE OF TuxTAppQEntry
        ACCESS  not-accessible
        STATUS  mandatory
        DESCRIPTION
                  " This table contains info about application queues. " 
        ::= { tuxTAppQ 1 }
 
tuxTAppQEntry OBJECT-TYPE
        SYNTAX TuxTAppQEntry
        ACCESS  not-accessible
        STATUS  mandatory
        DESCRIPTION
                  " A row in tuxTAppQTbl.
		Creation of a new row ( instance ):
		===================================
   For creating a new queue(row), in this group the SET request should
   have the value of tuxTAppQname , tuxTAppQspaceName & tuxTAppQmConfig.
   Also the value of tuxTAppQgrpNo (which is a part of the index) should
   be the corresponding group number for that queue space or `40000'.( if 
   no such group exists )
  
   NOTE 1: For this and all other AppQ MIB groups there is a control MIB which
   can be used to filter the data returned as a part of all AppQ MIB groups.

   NOTE 2: 	       All objects in this MIB group are local attributes i.e.
		       values for these objects correspond to the local host
		       only, where the TUXEDO agent is running. So the user needs
		       to run an instance of the TUXEDO agent on every node for
		       which these values are of interest."
        INDEX { tuxTAppQgrpNo , tuxTAppQname }
        ::= { tuxTAppQTbl 1 }
 
TuxTAppQEntry ::= SEQUENCE {
   tuxTAppQname
        DisplayString,
   tuxTAppQspaceName
        DisplayString,
   tuxTAppQmConfig
        DisplayString,
   tuxTAppQlmid
        DisplayString,
   tuxTAppQgrpNo
        INTEGER,
   tuxTAppQstate
        INTEGER,
   tuxTAppQorder
        DisplayString,
   tuxTAppQcmd
	DisplayString,
   tuxTAppQcmdHw
	DisplayString,
   tuxTAppQcmdLw
	DisplayString,
   tuxTAppQmaxRetries
	INTEGER,
   tuxTAppQoutOforder
	INTEGER,
   tuxTAppQretryDelay
	INTEGER,
   tuxTAppQcurBlocks
	INTEGER,
   tuxTAppQcurMsg
 	INTEGER,
   tuxTAppQDefExpirationTime
 	DisplayString,
   tuxTAppQDefDeliveryPolicy
 	INTEGER,
   tuxTAppQCmdNonPersist
 	DisplayString,
   tuxTAppQCmdNonPersistHw
	DisplayString,
   tuxTAppQCmdNonPersistLw
	DisplayString,
   tuxTAppQCurNonPersistBytes
	INTEGER,
   tuxTAppQCurNonPersistMsg
	INTEGER
   }
 
tuxTAppQname OBJECT-TYPE
        SYNTAX  DisplayString (SIZE(1..15))
        ACCESS  read-write	-- writable only during row creation
        STATUS  mandatory
        DESCRIPTION
		  "  Name of the application queue. 
		Note: This object can be set only during row creation."
	::= { tuxTAppQEntry 1 }

tuxTAppQspaceName OBJECT-TYPE
        SYNTAX  DisplayString (SIZE(1..15))
        ACCESS  read-write	-- writable only during row creation
        STATUS  mandatory
        DESCRIPTION
                  " Name of the  application  queue  space  containing  the
          	    application queue.
		Note: This object can be set only during row creation."
        ::= { tuxTAppQEntry 2 }

 tuxTAppQmConfig OBJECT-TYPE
        SYNTAX  DisplayString (SIZE(1..256))
        ACCESS  read-write	-- writable only during row creation
        STATUS  mandatory
        DESCRIPTION
                  " Absolute pathname of  the  file  or  device  where  the
          	    application queue space is located. 
		Note: This object can be set only during row creation."
        ::= { tuxTAppQEntry 3 }

 tuxTAppQlmid OBJECT-TYPE
        SYNTAX  DisplayString (SIZE(1..30))
        ACCESS  read-write	-- writable only during row creation
        STATUS  mandatory
        DESCRIPTION
                  " Identifier of the logical machine where the application
          	    queue space is located.
		Note: This object can be set only during row creation."
        ::= { tuxTAppQEntry 4 }

 tuxTAppQgrpNo OBJECT-TYPE
        SYNTAX  INTEGER (1..29999)
        ACCESS  read-write	-- writable only during row creation
        STATUS  mandatory
        DESCRIPTION
                  " Group number of any server group for which this queue is
		    a resource manager, in other words that group's openinfo
		    string tuxTgroupOpenInfo contains the device name and
		    queue space name for this queue.  
		Note: This object can be set only during row creation."
        ::= { tuxTAppQEntry 5 }
 
 tuxTAppQstate OBJECT-TYPE
        SYNTAX  INTEGER {
		valid(1),
		invalid(2)
		}
        ACCESS  read-write
        STATUS  mandatory
        DESCRIPTION
                  " 
	 GET: 
               A GET operation retrieves  information  about  the
               selected  application  queues.  The following list
               describes the meaning of  the tuxTAppQstate attribute
               returned in response to a GET request.  States not
               listed will not be returned.

               valid(1)     The  specified  queue  exists.

          SET: 
               A SET operation  changes  characteristics  of  the
               selected application queue or creates a new queue.
               The following list describes the  meaning  of  the
               tuxTAppQstate attribute  returned  by  a  SET request.
               States not listed can not be set.

               invalid(2)   Delete  the  specified  queue.
                            If  the  queue  space  has processes 
		 	    attached to it, the queue will not be deleted.
                            In addition, if the queue has messages 
			    in it, it will  not be deleted.
                            Successful  return  leaves the object in
                            the invalid(2) state. "
        ::= { tuxTAppQEntry 6 }

 tuxTAppQorder OBJECT-TYPE
        SYNTAX DisplayString (SIZE(1..30)) 
        ACCESS  read-write	-- writable only during row creation.
        STATUS  mandatory
        DESCRIPTION
                  " The order in which messages in the queue are to be pro-
          	    cessed.   Legal  values are PRIO or TIME, followed by a
          	    comma, optionally followed  by  another  occurrence  of
          	    PRIO  or  TIME,  followed  by one of the values LIFO or
          	    FIFO. If neither FIFO nor LIFO is  specified,  FIFO  is
          	    assumed.   If  nothing  is  specified  when  a queue is
          	    created, the default is FIFO.  For example,  these  are
          	    some legal settings:

             	     PRIO
             	     PRIO,TIME,LIFO
             	     TIME,PRIO,FIFO
             	     TIME,FIFO 
		     Note: This object can be updated only during row creat-
		     ion."
        ::= { tuxTAppQEntry 7 }

 tuxTAppQcmd OBJECT-TYPE
        SYNTAX  DisplayString (SIZE(0..127))
        ACCESS  read-write
        STATUS  mandatory
        DESCRIPTION
                  " The command to be automatically executed when the  high
          	    water  mark, tuxTAppQcmdHw, is reached.  The command will be
          	    re-executed when the high water mark is  reached  again
          	    after the low water mark, tuxTAppQcmdLw, has been reached. "
        ::= { tuxTAppQEntry 8 }
 		
 tuxTAppQcmdHw OBJECT-TYPE
        SYNTAX  DisplayString (SIZE(1..64))
        ACCESS  read-write
        STATUS  mandatory   
	DESCRIPTION
		"   See description of tuxTAppQcmdLw. "
        ::= { tuxTAppQEntry 9 }

   tuxTAppQcmdLw OBJECT-TYPE
        SYNTAX  DisplayString (SIZE(1..64))
        ACCESS  read-write
        STATUS  mandatory   
        DESCRIPTION
                  " The high and low water marks that control the automatic
          	    execution of the command specified in the tuxTAppQcmd 
		    attribute.  Each is an integer greater than or equal to 
		    zero optionally followed by one of the following keyle-
		    tters. The keyletters must  be  consistent  for  
		    tuxTAppQcmdHw and tuxTAppQcmdLw. 

          	    b    The high and low water marks pertain to the number
               	    of bytes used by messages in the queue.

          	    B    The high and low water marks pertain to the number
               	    of blocks used by messages in the queue.
	    
          	    m    The high and low water marks pertain to the number
               	    of messages in the queue.
	    
          	    %    The high and low  water  marks  are  expressed  in
               	    terms of a percentage of queue capacity.

     	    For example, if tuxTAppQcmdLw is 50m and tuxTAppQcmdHw is  100m,  
	    then the  command  specified  in tuxTAppQcmd will be executed when 
	    100 messages are on the queue, and it will not be executed again
     	    until  the  queue has been drained below 50 messages and has
     	    filled again to 100 messages."
        ::= { tuxTAppQEntry 10 }
 
   tuxTAppQmaxRetries OBJECT-TYPE 
        SYNTAX  INTEGER 
        ACCESS  read-write
        STATUS  mandatory    
        DESCRIPTION 
                  " The maximum number of retries for a failed  queue  mes-
          	    sage.   When  the  number  of retries is exhausted, the
          	    message is placed on the error queue of the  associated
          	    application  queue  space.  If there is no error queue,
          	    the message is dropped.  The default is zero. "
        ::= { tuxTAppQEntry 11 } 
   
   tuxTAppQoutOforder OBJECT-TYPE 
        SYNTAX  INTEGER {
		none(1),
		top(2),
		msgid(3)
		} 
        ACCESS  read-write
        STATUS  mandatory    
        DESCRIPTION 
                  " The way in which out-of-order message processing is  to
          	    be handled.  The default is none. "
        ::= { tuxTAppQEntry 12 } 
   
   tuxTAppQretryDelay OBJECT-TYPE 
        SYNTAX  INTEGER 
        ACCESS  read-write
        STATUS  mandatory    
        DESCRIPTION 
                  " The delay, in seconds, between  retries  for  a  failed
          	    queue message.  The default is zero. "
        ::= { tuxTAppQEntry 13 } 
   
   tuxTAppQcurBlocks OBJECT-TYPE 
        SYNTAX  INTEGER
        ACCESS  read-only
        STATUS  mandatory    
        DESCRIPTION 
                  " The number of disk  pages  currently  consumed  by  the
          	    queue. "
        ::= { tuxTAppQEntry 14 } 
   
   tuxTAppQcurMsg OBJECT-TYPE 
        SYNTAX  INTEGER 
        ACCESS  read-only
        STATUS  mandatory    
        DESCRIPTION 
                  " The number of messages currently in the queue. "
        ::= { tuxTAppQEntry 15 } 
   
-- Added : START-JANUS-NS-TUXEDO7.1-041400

   tuxTAppQDefExpirationTime OBJECT-TYPE 
        SYNTAX  DisplayString 
        ACCESS  read-write
        STATUS  mandatory    
        DESCRIPTION 
     "This attribute specifies an expiration time for messages enqueued with
     no explicit expiration time. The expiration time may be either a
     relative expiration time or none. The relative expiration time is
     determined by associating a fixed amount of time with a message after
      the message arrives at the queue manager process. When a message's
      expiration time is reached and the message has not been dequeued or
      administratively deleted, all resources associated with the message are
      reclaimed by the system and statistics are updated. If a message
      expires during a transaction, the expiration does not cause the
      transaction to fail. Messages that expire while being enqueued or
      dequeued within a transaction are removed from the queue when the
      transaction ends. There is no notification that the message has
      expired. If no default expiration time is specified for a queue, then
      messages without an explicit expiration time do not expire. When the
      queue's expiration time is modified, the expiration times of messages
      that were in the queue before the modification are not changed.
 
      The format is +seconds where seconds is the number of seconds allowed
      to lapse between the time that the queue manager successfully completes
      the operation and the time that the message is to expire. If seconds is
      set to zero (0) the message expires immediately.
 
      The value of this attribute may also be set to the string none. The
      none string indicates that messages enqueued to the queue with no
      explicit expiration time do not expire. You may change the expiration
      time for messages already in a queue with the tuxTAppQmsgExpireTime object
      of the tuxTAppQmsgTbl group"
         ::= { tuxTAppQEntry 30 } 
    
    tuxTAppQDefDeliveryPolicy OBJECT-TYPE 
         SYNTAX  INTEGER {
 		persist (1),
 		non-persist (2)
 	}
         ACCESS  read-write
         STATUS  mandatory    
         DESCRIPTION 
      "This attribute specifies the default delivery policy for the queue when
      no delivery mode is specified for a message enqueued to the queue. When
      the value is persist, messages enqueued to the queue without an
      explicitly specified delivery mode are delivered using the persistent
      (disk-based) delivery method. When the value is non-persist, messages
      enqueued to the queue without an explicitly specified delivery mode are
      delivered using the non-persistent (in memory) delivery method.When a
      queue's default delivery policy is modified, the delivery quality of
      service of messages that are in the queue before the modification are
      not changed. If the queue being modified is the reply queue named for
      any messages currently in the queue space, the reply quality of service
      is not changed for those messages as a result of changing the default
      delivery policy of the queue.
 
      For non-persistent delivery, if the memory area is exhausted or
      fragmented such that a message cannot be enqueued, the enqueuing
      operation fails, even if there is sufficient persistent storage for the
      message. Similarly, if the persistent storage area is exhausted or
      fragmented such that a message cannot be enqueued, the enqueuing
      operation fails, even if there is sufficient non-persistent storage for
      the message. If the tuxTQspaceMemNonPersist object of the tuxTQspaceTbl 
      group is zero (0) for a queue space, no space is reserved for 
	non-persistent
      messages. In such a case, any attempt to enqueue a non-persistent
      message fails. This type of failure results, for example, when no
      delivery quality of service has been specified for a message and the
      tuxTAppQDefDeliveryPolicy object for the target queue has been set to
      non-persist."
         ::= { tuxTAppQEntry 40 } 
    
    tuxTAppQCmdNonPersist OBJECT-TYPE 
         SYNTAX  DisplayString (SIZE(0..127))
         ACCESS  read-write
         STATUS  mandatory    
         DESCRIPTION 
      "This attribute specifies the command to be executed automatically when
      the high-water mark for non-persistent (memory-based delivery)
      messages, tuxTAppQCmdNonPersistHw, is reached. The command is re-executed
      when the high-water mark is reached again after the low-water mark for
      non-persistent (memory-based delivery) messages, tuxTAppQCmdNonPersistLw,
      has been reached."
         ::= { tuxTAppQEntry 50 } 
    
    tuxTAppQCmdNonPersistHw OBJECT-TYPE 
         SYNTAX  DisplayString
         ACCESS  read-write
         STATUS  mandatory    
         DESCRIPTION 
      "These attributes specify the high- and low-water marks that control the
      automatic execution of the command specified in the tuxTAppQCmdNonPersist
      attribute. Each is an integer greater than or equal to zero followed by
      one of the following keyletters. The keyletters must be consistent for
      tuxTAppQCmdNonPersistHw and tuxTAppQCmdNonPersistLw.
 
      b
 
           The high- and low-water marks are expressed as the number of bytes
           used by non-persistent (in memory) messages in the queue.
 
      B
 
           The high- and low-water marks are expressed as the number of
           blocks used by non-persistent (in memory) messages in the queue.
 
      %
 
           The high- and low-water marks are expressed as a percentage of the
           shared memory capacity reserved for non-persistent messages in the
           queue space used by the queue.
 
           The messages threshold type specified via the tuxTAppQcmdHw and
           tuxTAppQcmdLw attributes (when followed by an m) applies to all
           messages in a queue, including both persistent and non-persistent
           messages, and therefore is not available as a threshold type for
           tuxTAppQCmdNonPersistHw and tuxTAppQCmdNonPersistLw."
         ::= { tuxTAppQEntry 60 } 
    
    tuxTAppQCmdNonPersistLw OBJECT-TYPE 
         SYNTAX  DisplayString
         ACCESS  read-write
         STATUS  mandatory    
         DESCRIPTION 
      "These attributes specify the high- and low-water marks that control the
      automatic execution of the command specified in the tuxTAppQCmdNonPersist
      attribute. Each is an integer greater than or equal to zero followed by
      one of the following keyletters. The keyletters must be consistent for
      tuxTAppQCmdNonPersistHw and tuxTAppQCmdNonPersistLw.
 
      b
 
           The high- and low-water marks are expressed as the number of bytes
           used by non-persistent (in memory) messages in the queue.
 
      B
 
           The high- and low-water marks are expressed as the number of
           blocks used by non-persistent (in memory) messages in the queue.
 
      %
 
           The high- and low-water marks are expressed as a percentage of the
           shared memory capacity reserved for non-persistent messages in the
           queue space used by the queue.
 
           The messages threshold type specified via the tuxTAppQcmdHw and
           tuxTAppQcmdLw attributes (when followed by an m) applies to all
           messages in a queue, including both persistent and non-persistent
           messages, and therefore is not available as a threshold type for
           tuxTAppQCmdNonPersistHw and TtuxTAppQCmdNonPersistLw."
         ::= { tuxTAppQEntry 70 } 
    
    tuxTAppQCurNonPersistBytes OBJECT-TYPE 
         SYNTAX  INTEGER 
         ACCESS  read-only
         STATUS  mandatory    
         DESCRIPTION 
      "This attribute specifies the number of shared memory bytes currently
      consumed by the non-persistent messages on the queue."
         ::= { tuxTAppQEntry 80 } 
    
    tuxTAppQCurNonPersistMsg OBJECT-TYPE 
         SYNTAX  INTEGER 
         ACCESS  read-only
         STATUS  mandatory    
         DESCRIPTION 
      "This attribute specifies the number of non-persistent messages
      currently in the queue. To determine the total number of messages in
      the queue, add tuxTAppQcurMsg to this value."
         ::= { tuxTAppQEntry 90 } 
    
-- Added : END-JANUS-NS-TUXEDO7.1-041400
 
--************************************************************************** 
--   tuxTAppQmsg
--   The tuxTAppQmsg group represents messages stored  in  applica-
--   tion  queues.  A message is not created by an administrator;
--   instead, it comes into existence as a result of  a  call  to
--   tpenqueue(3).   A  message can be destroyed either by a call
--   to tpdequeue(3) or by an administrator.  In  addition,  cer-
--   tain  attributes of a message can be modified by an adminis-
--   trator.  For example, an administrator can  move  a  message
--   from  one queue to another queue within the same queue space
--   or change its priority.
--
--**************************************************************************

tuxTAppQmsgTbl OBJECT-TYPE
        SYNTAX  SEQUENCE OF TuxTAppQmsgEntry
        ACCESS  not-accessible
        STATUS  mandatory
        DESCRIPTION
                  "This table contains info about application queue messages."
        ::= { tuxTAppQ 2 }
 
tuxTAppQmsgEntry OBJECT-TYPE
        SYNTAX TuxTAppQmsgEntry
        ACCESS  not-accessible
        STATUS  mandatory
        DESCRIPTION
                  " A row in tuxTAppQmsgTbl. 
		    Note: The values returned by this MIB are controlled by 
		    tuxTAppQctrl. Refer to the description of the above group 
		    for details.

		 NOTE: All objects in this MIB group are local attributes i.e.
		       values for these objects correspond to the local host
		       only, where the TUXEDO agent is running. So the user needs
		       to run an instance of the TUXEDO agent on every node for
		       which these values are of interest."
        INDEX { tuxTAppQmsgGrpNo , tuxTAppQmsgQname , tuxTAppQmsgSerNo }
        ::= { tuxTAppQmsgTbl 1 }
 
TuxTAppQmsgEntry ::= SEQUENCE {
   tuxTAppQmsgId
        DisplayString,
   tuxTAppQmsgSerNo
        INTEGER,
   tuxTAppQmsgGrpNo
        INTEGER,
   tuxTAppQmsgQname
        DisplayString,
   tuxTAppQmsgQmConfig
        DisplayString,
   tuxTAppQmsgQspaceName
        DisplayString,
   tuxTAppQmsgLmid
        DisplayString,
   tuxTAppQmsgState
        INTEGER,
   tuxTAppQmsgNewQname
        DisplayString,
   tuxTAppQmsgPrior
        INTEGER,
   tuxTAppQmsgTime
        DisplayString,
   tuxTAppQmsgCorId
	DisplayString,
   tuxTAppQmsgCurRetries
	INTEGER,
   tuxTAppQmsgSize
	INTEGER,
   tuxTAppQmsgExpireTime
        DisplayString,
   tuxTAppQmsgPersistent
	INTEGER,
   tuxTAppQmsgReplyPersistent
	INTEGER
   }

tuxTAppQmsgId OBJECT-TYPE
        SYNTAX DisplayString (SIZE(1..32))
        ACCESS  read-only
        STATUS  mandatory
        DESCRIPTION
                  " A unique identifier for the queue message, which can be
          	    used  to  select the message for GET or SET operations.
          	    No significance should be placed on this  value  beyond
          	    using it for equality comparisons. " 
        ::= { tuxTAppQmsgEntry 1 }

tuxTAppQmsgSerNo OBJECT-TYPE
        SYNTAX  INTEGER 
        ACCESS  read-only
        STATUS  mandatory
        DESCRIPTION
                  " A running number corresponding to tuxTAppQmsgId for the 
		    queue message, which is a part of the composite index of 
		    this table" 
        ::= { tuxTAppQmsgEntry 2 }
 
tuxTAppQmsgGrpNo OBJECT-TYPE
        SYNTAX  INTEGER
        ACCESS  read-only
        STATUS  mandatory
        DESCRIPTION
                  " Group number of any server group for which this queue is
                    a resource manager, in other words that group's openinfo
                    string tuxTgroupOpenInfo contains the device name and
                    queue space name for this queue. "
        ::= { tuxTAppQmsgEntry 3 }
 
tuxTAppQmsgQname OBJECT-TYPE
        SYNTAX DisplayString (SIZE(1..15))
        ACCESS  read-only
        STATUS  mandatory
        DESCRIPTION
                  " Name of the application queue in which the  message  is
          	    stored. "
        ::= { tuxTAppQmsgEntry 4 } 
  
tuxTAppQmsgQmConfig OBJECT-TYPE
        SYNTAX DisplayString (SIZE(1..256))
        ACCESS  read-only
        STATUS  mandatory
        DESCRIPTION  
                  " Absolute pathname of  the  file  or  device  where  the
                    application queue space for the queue containing this 
		    message is located. "
        ::= { tuxTAppQmsgEntry 5 }
 
tuxTAppQmsgQspaceName OBJECT-TYPE
        SYNTAX DisplayString (SIZE(1..15))
        ACCESS  read-only
        STATUS  mandatory
        DESCRIPTION  
                  " Name of the  application  queue  space  containing  the
                    application queue in which this message is located. "
        ::= { tuxTAppQmsgEntry 6 }
 
tuxTAppQmsgLmid OBJECT-TYPE
        SYNTAX  DisplayString (SIZE(1..30))
        ACCESS  read-only
        STATUS  mandatory
        DESCRIPTION  
                  " Logical machine id for the machine on which the queue 
		    containing this message is located. "
        ::= { tuxTAppQmsgEntry 7 }
 

tuxTAppQmsgState OBJECT-TYPE 
        SYNTAX INTEGER {
		valid(1),
		invalid(2)
		}
        ACCESS  read-write
        STATUS  mandatory  
        DESCRIPTION 
                  " 
         GET:
               A GET operation retrieves  information  about  the
               selected  messages.   The following list describes
               the meaning of the tuxTAppQmsgState attribute returned in
               response to a GET request. States not listed will
               not be returned.

               valid(1)     The message exists.   

          SET:
               A SET operation  changes  characteristics  of  the
               selected  message.   The  following list describes
               the meaning of the tuxTAppQmsgState attribute returned  by
               a SET request.  States not listed can not be set.

               invalid(2)   The message is deleted from its queue
                            space.   The message must be in state
                            valid(1) before attempting  this  opera-
                            tion.   Successful  return leaves the
                            object in the invalid(2) state. "
        ::= { tuxTAppQmsgEntry 8 } 
  
tuxTAppQmsgNewQname OBJECT-TYPE 
	SYNTAX DisplayString (SIZE(1..15))
	ACCESS  read-write
	STATUS  mandatory  
	DESCRIPTION
                  " Name of the queue into which to move the selected  mes-
          	    sage.  This queue must be an existing queue in the same
          	    queue space.  The message must be in  state  VALid  for
          	    this  operation  to  succeed.   This  attribute  is not
          	    returned by a GET operation. "
        ::= { tuxTAppQmsgEntry 9 } 
  
tuxTAppQmsgPrior OBJECT-TYPE 
        SYNTAX INTEGER
        ACCESS  read-write
        STATUS  mandatory  
        DESCRIPTION 
                  " The priority of the message.  This attribute  is  valid
          	    only  for  PRIO-based queues.  The value -1 is returned
          	    by a GET operation if the queue is not PRIO-based. "
        ::= { tuxTAppQmsgEntry 10 } 
  
tuxTAppQmsgTime OBJECT-TYPE 
        SYNTAX DisplayString (SIZE(1..15))
        ACCESS  read-write
        STATUS  mandatory  
        DESCRIPTION 
                  " The time when the  message  will  be  processed.   This
          	    attribute  is  valid  only  for TIME-based queues.  The
          	    empty string is returned by  a  GET  operation  if  the
          	    queue is not TIME-based.  The format is one of the fol-
          	    lowing:

          	    +seconds
               	    Specifies  that  the  message  will  be  processed
               	    seconds  in  the future.  The value zero specifies
               	    that the message should be processed immediately.
	    
          	    YY[MM[DD[hh[mm[ss]]]]]
               	    Specifies the year, month, day, hour, minute,  and
               	    second  when  the  message  should  be  processed.
               	    Omitted units default to  their  minimum  possible
               	    values.    For  example,  9506  is  equivalent  to
               	    950601000000.  The years 00 through 37 are treated
               	    as  2000  through 20037, 70 through 99 are treated
               	    as 1970  through  1999,  and  38  through  69  are
               	    invalid. "
        ::= { tuxTAppQmsgEntry 11 } 
  
tuxTAppQmsgCorId OBJECT-TYPE 
        SYNTAX DisplayString (SIZE(0..32))
        ACCESS  read-only
        STATUS  mandatory  
        DESCRIPTION 
                  " The correlation identifier for this message provided by
          	   the application in the tpenqueue(3) request.  The empty
          	   string indicates that a correlation identifier  is  not
          	   present. "
        ::= { tuxTAppQmsgEntry 12 } 
  
tuxTAppQmsgCurRetries OBJECT-TYPE 
        SYNTAX  INTEGER 
        ACCESS  read-only
        STATUS  mandatory     
        DESCRIPTION 
                  "  The number of retries that have been attempted  so  far
          	     on this message. "
        ::= { tuxTAppQmsgEntry 13 } 
  
tuxTAppQmsgSize OBJECT-TYPE 
        SYNTAX  INTEGER 
        ACCESS  read-only
        STATUS  mandatory     
        DESCRIPTION 
                  "  The size of the message, in bytes. "
        ::= { tuxTAppQmsgEntry 14 } 
  
-- Added : START-JANUS-NS-TUXEDO7.1-041400

tuxTAppQmsgExpireTime OBJECT-TYPE 
        SYNTAX DisplayString (SIZE(1..15))
         ACCESS  read-write
         STATUS  mandatory     
         DESCRIPTION 
      "This attribute specifies the time at which a message expires (that is,
      the time at which the message should be removed from the queue if it
      has not already been dequeued or administratively deleted). When a
      message expires, all resources used by it are reclaimed by the system
      and statistics are updated. If a message expires during a transaction,
      the expiration does not cause the transaction to fail. Messages that
      expire while being enqueued or dequeued within a transaction are
      removed from the queue when the transaction ends. There is no
      notification that the message has expired.
      Expiration times cannot be added to messages enqueued by versions of
      the BEA Tuxedo system that do not support message expiration, even when
      the queue manager responsible for changing this value supports message
      expiration. Attempts to add an expiration time fail.
 
      The empty string is returned by a GET operation if the expiration time
      is not set. The expiration time format is one of the following.
 
      +seconds
 
           Specifies that the message will be removed after the specified
           number of seconds. If the value of seconds is set to zero (0), the
           message is removed immediately from the queue. Relative expiration
           time is calculated on the basis of the time at which the MIB
           request arrives and has been processed by the corresponding queue
           manager.
 
      YY[MM[DD[hh]mm[ss]]]]
 
           Specifies the year, month, day, hour, minute, and second when the
           message will be removed if it has not been dequeued or
           administratively deleted already. Omitted units default to their
           minimum possible values. For example, 9506 is equivalent to
           950601000000. The years 00 through 37 are treated as 2000 through
           2037, 70 through 99 are treated as 1970 through 1999, and 38
           through 69 are invalid. An absolute expiration time is determined
           by the clock on the machine where the queue manager process
           resides.
 
      none
 
           Specifies that the message will never expire."
         ::= { tuxTAppQmsgEntry 20 } 
   
tuxTAppQmsgPersistent OBJECT-TYPE 
         SYNTAX  INTEGER {
		yes(1),
		no(2)
 	}
         ACCESS  read-only
         STATUS  mandatory     
         DESCRIPTION 
      "This read-only state is set to 'no for non-persistent messages and 'yes' for
      persistent messages. It is the delivery quality of service
      for the message."
         ::= { tuxTAppQmsgEntry 30 } 
   
tuxTAppQmsgReplyPersistent OBJECT-TYPE 
        SYNTAX  INTEGER {
		yes(1),
		no(2)
	}
        ACCESS  read-only
        STATUS  mandatory     
        DESCRIPTION 
     "This read-only state is set to no for non-persistent and yes for
     persistent. It is the delivery quality that replies to
     the message should be delivered with."
        ::= { tuxTAppQmsgEntry 40 } 

-- Added : END-JANUS-NS-TUXEDO7.1-041400

--**************************************************************************
--   tuxTQspace group
--   This group represents application queue spaces.
--
--**************************************************************************

tuxTQspaceTbl OBJECT-TYPE
        SYNTAX  SEQUENCE OF TuxTQspaceEntry
        ACCESS  not-accessible
        STATUS  mandatory
        DESCRIPTION
                  "This table contains info about application queue spaces."
        ::= { tuxTAppQ 3 }

tuxTQspaceEntry OBJECT-TYPE
        SYNTAX TuxTQspaceEntry
        ACCESS  not-accessible
        STATUS  mandatory
        DESCRIPTION
                  " A row in tuxTQspaceTbl. 
     Creation of a new row (instance):
     ================================
     The user should send a set request with an index (tuxTQspaceGrpNo) of
     `40000'. This is a reserved value for row creation in this table.
     The newly created instance will be not be visible until it is attached
     to some server group. To create a new instance the user needs to specify
     atleast tuxTQspaceQmConfig, tuxTQspaceName, tuxTQspaceLmid, tuxTQspace-
     Ipckey, tuxTQspaceMaxMsg, tuxTQspaceMaxPages, tuxTQspaceMaxProc, 
     tuxTQspaceMaxQueues and tuxTQspaceMaxTrans. 
   
     NOTE 1: The values returned by this MIB are controlled by tuxTAppQctrl. 
	     Refer to the description of the above group for details.

     NOTE 2: 	       All objects in this MIB group are local attributes i.e.
		       values for these objects correspond to the local host
		       only, where the TUXEDO agent is running. So the user needs
		       to run an instance of the TUXEDO agent on every node for
		       which these values are of interest."
        INDEX { tuxTQspaceGrpNo }
        ::= { tuxTQspaceTbl 1 }

TuxTQspaceEntry ::= SEQUENCE {
   tuxTQspaceName
        DisplayString,
   tuxTQspaceQmConfig
        DisplayString,
   tuxTQspaceLmid
        DisplayString,
   tuxTQspaceGrpNo
        INTEGER,
   tuxTQspaceState
        INTEGER,
   tuxTQspaceBlocking
        INTEGER,
   tuxTQspaceErrQname
        DisplayString,
   tuxTQspaceForceInit
        INTEGER,
   tuxTQspaceIpckey
        INTEGER,
   tuxTQspaceMaxMsg
	INTEGER,
   tuxTQspaceMaxPages
	INTEGER,
   tuxTQspaceMaxProc
	INTEGER,
   tuxTQspaceMaxQueues
	INTEGER,
   tuxTQspaceMaxTrans
	INTEGER,
   tuxTQspaceCurExtent
	INTEGER,
   tuxTQspaceCurMsg
	INTEGER,
   tuxTQspaceCurProc
	INTEGER,
   tuxTQspaceCurQueues
	INTEGER,
   tuxTQspaceCurTrans
	INTEGER,
   tuxTQspaceHwMsg
	INTEGER,
   tuxTQspaceHwProc
	INTEGER,
   tuxTQspaceHwQueues
	INTEGER,
   tuxTQspaceHwTrans
	INTEGER,
   tuxTQspacePercentInit
	INTEGER,
   tuxTQspaceMaxActions
	INTEGER,
   tuxTQspaceMaxHandles
	INTEGER,
   tuxTQspaceMaxOwners
	INTEGER,
   tuxTQspaceMaxTmpQueues
	INTEGER,
   tuxTQspaceMaxCursors
	INTEGER,
   tuxTQspaceMemNonPersist
        DisplayString ,
   tuxTQspaceMemFilters
	INTEGER,
   tuxTQspaceMemOverFlow
	INTEGER,
   tuxTQspaceMemSystemReserved
	INTEGER,
   tuxTQspaceMemTotalAllocated
	INTEGER,
   tuxTQspaceCurActions
	INTEGER,
   tuxTQspaceCurHandles
	INTEGER,
   tuxTQspaceCurOwners
	INTEGER,
   tuxTQspaceCurTmpQueues
	INTEGER,
   tuxTQspaceCurCursors
	INTEGER,
   tuxTQspaceCurMemNonPersist
	INTEGER,
   tuxTQspaceCurMemFilters
	INTEGER,
   tuxTQspaceCurMemOverFlow
	INTEGER,
   tuxTQspaceHwActions
	INTEGER,
   tuxTQspaceHwHandles
	INTEGER,
   tuxTQspaceHwOwners
	INTEGER,
   tuxTQspaceHwTmpQueues
	INTEGER,
   tuxTQspaceHwCursors
	INTEGER,
   tuxTQspaceHwMemNonPersist
	INTEGER,
   tuxTQspaceHwMemFilters
	INTEGER,
   tuxTQspaceHwMemOverFlow
	INTEGER
	}

tuxTQspaceName OBJECT-TYPE
        SYNTAX 	DisplayString (SIZE(1..15))
        ACCESS 	read-write	-- writable only during row creation
        STATUS 	mandatory
        DESCRIPTION
                  " Name of the application queue space. 
		Note: This object can be set only during row creation."
        ::= { tuxTQspaceEntry 1 }
 
tuxTQspaceQmConfig OBJECT-TYPE 
        SYNTAX 	DisplayString (SIZE(1..256))
        ACCESS 	read-write	-- writable only during row creation
        STATUS 	mandatory 
        DESCRIPTION 
                  " Absolute pathname of  the  file  or  device  where  the
          	    application queue space is located.
		Note: This object can be set only during row creation."
        ::= { tuxTQspaceEntry 2 } 
  
tuxTQspaceLmid OBJECT-TYPE 
        SYNTAX 	DisplayString (SIZE(1..30))
        ACCESS  read-write	-- writable only during row creation
        STATUS  mandatory 
        DESCRIPTION 
                  " Identifier of the logical machine where the application
          	    queue space is located. 
		Note: This object can be set only during row creation."
        ::= { tuxTQspaceEntry 3 } 
 
tuxTQspaceGrpNo OBJECT-TYPE
        SYNTAX  INTEGER (1..29999)
        ACCESS  read-write	-- writable only during row creation
        STATUS  mandatory
        DESCRIPTION
                  " Group number of any server group for which this queue space
                    is a resource manager, in other words that group's openinfo
                    string tuxTgroupOpenInfo contains the device name and
                    queue space name for this queue space. 
		Note: This object can be set only during row creation."
        ::= { tuxTQspaceEntry 4 }
 
 
tuxTQspaceState OBJECT-TYPE 
        SYNTAX 	INTEGER {
		inactive(1),
		initializing(2),
		open(3),
		active(4),
		cleaning(5),
		invalid(6)
		}
        ACCESS  read-write
        STATUS  mandatory 
        DESCRIPTION 
                  "
          GET:
               A GET operation retrieves  information  about  the
               selected  application  queue space.  The following
               list describes the meaning of the tuxTQspaceState attri-
               bute  returned  in  response  to  a  GET  request.
               States not listed will not be returned.

               inactive(1)  The queue space  exists;  i.e.,  disk
                            space  for  it has been reserved in a
                            device and the space  has  been  ini-
                            tialized  (if  requested or if neces-
                            sary).

               initializing(2)
			    Disk space for  the  queue  space  is
                            currently  being  initialized. 

               open(3)      Shared memory and other IPC resources
                            for  the  queue space have been allo-
                            cated   and   initialized,   but   no
                            processes  are  currently attached to
                            the shared  memory. 

               active(4)    Shared memory and other IPC resources
                            for  the  queue space have been allo-
                            cated and initialized, and  at  least
                            one  process is currently attached to
                            the shared memory.   These  processes
                            can  be  the  queue  servers (TMS_QM,
                            TMQUEUE,  and   perhaps   TMQFORWARD)
                            associated  with  the queue space, or
                            they can be administrative  processes
                            such  as  qmadmin(1),  or they can be
                            processes  associated  with   another
                            application.
          SET: 
               A SET operation changes the  selected  application
               queue  space  or creates a new one.  The following
               list describes the meaning of the tuxTQspaceState attri-
               bute returned by a SET request.  States not listed
               can not be set.

               open(3)      Allocate and initialize shared memory
                            and other IPC resources for the queue
                            space.  This is allowed only  if  the
                            queue space is in the inactive(1) state.

               cleaning(5)  Remove the shared  memory  and  other
                            IPC  resources  for  the queue space.
                            This is allowed only when  the  queue
                            space is in the open(3) or active(4) 
		   	    state. 
                            Successful return leaves  the  object
                            in the inactive(2) state.

               invalid(6)   Delete the queue space. An error is reported  
			    if  the  state  is active(4) or if messages 
			    exist on any queues in the queue space.   
			    Successful  return  leaves the object in the
                            invalid(6) state. "
        ::= { tuxTQspaceEntry 5 } 
  
tuxTQspaceBlocking OBJECT-TYPE 
        SYNTAX 	INTEGER
        ACCESS  read-write
        STATUS  mandatory 
        DESCRIPTION 
                  " The blocking factor used for disk space  management  of
          	    the queue space.  The default when a new queue space is
          	    created is 16. " 
        ::= { tuxTQspaceEntry 6 } 
  
tuxTQspaceErrQname OBJECT-TYPE 
        SYNTAX DisplayString (SIZE(0..15))
        ACCESS  read-write
        STATUS  mandatory 
        DESCRIPTION 
                  " Name of the  error  queue  associated  with  the  queue
          	    space.   If there is no error queue, an empty string is
          	    returned by a GET request. "
        ::= { tuxTQspaceEntry 7 } 
  
tuxTQspaceForceInit OBJECT-TYPE 
        SYNTAX	INTEGER {
		yes(1),
		no(2)
		} 
        ACCESS  read-write
        STATUS  mandatory 
        DESCRIPTION 
                  " Whether or not to initialize disk pages on new  extents
          	    for the queue space.  The default is not to initialize.
          	    Depending on the device type (e.g., regular file or raw
          	    slice), initialization can occur even if not requested. "
        ::= { tuxTQspaceEntry 8 } 
  
tuxTQspaceIpckey OBJECT-TYPE 
        SYNTAX	INTEGER (32769..262143) 
        ACCESS  read-write
        STATUS  mandatory 
        DESCRIPTION 
                  " The IPC key used to access queue space shared memory. " 
        ::= { tuxTQspaceEntry 9 } 
  
tuxTQspaceMaxMsg OBJECT-TYPE 
        SYNTAX	INTEGER 
        ACCESS  read-write
        STATUS  mandatory 
        DESCRIPTION 
                  " The maximum number of messages that the queue space can
          	    contain. "
        ::= { tuxTQspaceEntry 10 } 
  
tuxTQspaceMaxPages OBJECT-TYPE 
        SYNTAX	INTEGER 
        ACCESS  read-write
        STATUS  mandatory 
        DESCRIPTION 
                  " The maximum number of disk pages for all queues in  the
          	    queue  space.   Each  time this object is
          	    increased,   a   new   extent   is    allocated    (see
          	    tuxTQspaceCurExtent). It is not possible to decrease the
          	    number of pages by setting this attribute  to  a  lower
          	    number; an error is reported in this case."
        ::= { tuxTQspaceEntry 11 } 
  
tuxTQspaceMaxProc OBJECT-TYPE 
        SYNTAX	INTEGER 
        ACCESS  read-write
        STATUS  mandatory 
        DESCRIPTION 
                  " The maximum number of processes that can attach to  the
          	    queue space. " 
        ::= { tuxTQspaceEntry 12 } 
  
tuxTQspaceMaxQueues OBJECT-TYPE 
        SYNTAX	INTEGER 
        ACCESS  read-write
        STATUS  mandatory 
        DESCRIPTION 
                  " The maximum number of queues that the queue  space  can
          	    contain. " 
        ::= { tuxTQspaceEntry 13 } 
  
tuxTQspaceMaxTrans OBJECT-TYPE 
        SYNTAX  INTEGER	
        ACCESS  read-write
        STATUS  mandatory 
        DESCRIPTION 
                  " The maximum number of  simultaneously  active  transac-
          	    tions allowed by the queue space. "
        ::= { tuxTQspaceEntry 14 } 
  
tuxTQspaceCurExtent OBJECT-TYPE 
        SYNTAX  INTEGER	
        ACCESS  read-only
        STATUS  mandatory 
        DESCRIPTION 
                  " The current number of extents used by the queue  space.
          	    The  largest  number  allowed  is  100.  Each  time the
          	    tuxTQspaceMaxPages variable is increased,  a  new  extent  
			is allocated. "
        ::= { tuxTQspaceEntry 15 } 
  
tuxTQspaceCurMsg OBJECT-TYPE 
        SYNTAX  INTEGER	
        ACCESS  read-only
        STATUS  mandatory 
        DESCRIPTION 
                  " The current number of  messages  in  the  queue  space.
          	    This  number  can be determined only if the queue space
          	    is OPEn or ACTive, or  if  the  queue  space  is  newly
          	    created.  If none of the conditions apply, the value -1
          	    is returned. " 
        ::= { tuxTQspaceEntry 16 } 
  
tuxTQspaceCurProc OBJECT-TYPE 
        SYNTAX  INTEGER     
        ACCESS  read-only
        STATUS  mandatory 
        DESCRIPTION 
                  " The current number of  processes  accessing  the  queue
          	    space. "
        ::= { tuxTQspaceEntry 17 }
 
tuxTQspaceCurQueues OBJECT-TYPE 
        SYNTAX  INTEGER     
        ACCESS  read-only
        STATUS  mandatory 
        DESCRIPTION 
                  " The current number of  queues  existing  in  the  queue
          	    space.  This number can be determined only if the queue
          	    space is OPEn or ACTive, or if the queue space is newly
          	    created.   If none of these conditions apply, the value
          	    -1 is returned. "
        ::= { tuxTQspaceEntry 18 }
 
tuxTQspaceCurTrans OBJECT-TYPE 
        SYNTAX  INTEGER     
        ACCESS  read-only
        STATUS  mandatory 
        DESCRIPTION 
                  " The current number of outstanding transactions  involv-
          	    ing the queue space. "
        ::= { tuxTQspaceEntry 19 }
 
tuxTQspaceHwMsg OBJECT-TYPE 
        SYNTAX  INTEGER     
        ACCESS  read-only
        STATUS  mandatory 
        DESCRIPTION 
                  " The highest number of messages in the queue space since
          	    the  queue  space was last opened.  The number is reset
          	    to 0 when the queue space state is set to CLEaning. "
        ::= { tuxTQspaceEntry 20 }
 
tuxTQspaceHwProc OBJECT-TYPE 
        SYNTAX  INTEGER     
        ACCESS  read-only
        STATUS  mandatory 
        DESCRIPTION 
                  " The highest number of processes simultaneously attached
          	    to  the  queue  space  since  the  queue space was last
          	    opened.  The number is reset to 0 when the queue  space
          	    state is set to CLEaning. "
        ::= { tuxTQspaceEntry 21 }
 
tuxTQspaceHwQueues OBJECT-TYPE 
        SYNTAX  INTEGER     
        ACCESS  read-only
        STATUS  mandatory 
        DESCRIPTION 
                  " The highest number of  queues  existing  in  the  queue
          	    space  since  the  queue  space  was  last opened.  The
          	    number is reset to 0 when the queue space state is  set
          	    to CLEaning. "
        ::= { tuxTQspaceEntry 22 }
 
tuxTQspaceHwTrans OBJECT-TYPE 
        SYNTAX  INTEGER     
        ACCESS  read-only
        STATUS  mandatory 
        DESCRIPTION 
                  " The highest number of outstanding transactions  involv-
          	    ing  the  queue  space  since  the queue space was last
          	    opened.  If the queue space is accessed  by  more  than
          	    one  application, this number reflects all applications
          	    - not just the application represented by the TUXCONFIG
          	    environment  variable.   The  number is reset to 0 when
          	    the queue space state is set to cleaning(5). "
        ::= { tuxTQspaceEntry 23 }
 
tuxTQspacePercentInit OBJECT-TYPE 
        SYNTAX  INTEGER (0..100)    
        ACCESS  read-only
        STATUS  mandatory 
        DESCRIPTION 
                  " The current number of  messages  in  the  queue  space. 
                    This  number  can be determined only if the queue space
                    is OPEn or ACTive, or  if  the  queue  space  is  newly
                    created.  If none of the conditions apply, the value -1 
                    is returned. " 
        ::= { tuxTQspaceEntry 24 }
 
-- Added : START-JANUS-NS-TUXEDO7.1-041400

tuxTQspaceMaxActions OBJECT-TYPE 
        SYNTAX  INTEGER 
        ACCESS  read-write
        STATUS  mandatory 
        DESCRIPTION 
     "This attribute specifies the number of additional actions that the
     Queuing Services component of the BEA Engine can handle concurrently.
     When a blocking operation is encountered and additional actions are
     available, the blocking operation is set aside until it can be
     satisfied. After setting aside the blocking operation, another
     operation request can be handled. When the blocking operation
     completes, the action associated with the operation is made available
     for a subsequent operation. The system reserves actions equivalent to
     the number of processes that can attach to a queue space, so that each
     queue manager process may have at least one blocking action. Beyond the
     system-reserved number of blocking actions, the administrator may
     configure the system to be able to accommodate additional blocking
     actions beyond the reserve. An operation fails if a blocking operation
     is requested and cannot be immediately satisfied and there are no
     actions available."
        ::= { tuxTQspaceEntry 40 }
 
tuxTQspaceMaxHandles OBJECT-TYPE 
        SYNTAX  INTEGER 
        ACCESS  read-write
        STATUS  mandatory 
        DESCRIPTION 
     "This attribute specifies the number of handles that users of that the
     Queuing Services component of the BEA Engine may use concurrently.
     Objects manipulated by the queuing services API require handles to
     access the objects. When an object is opened by a call to the Queuing
     Services API, a new handle is created and returned to the user. When an
     object handle is closed, the handle is made available for subsequent
     open object operations. When the Queuing Services API is used by an
     application, the administrator must configure the system to accommodate
     the maximum number of handles that will be opened concurrently. An
     operation fails if a user attempts to open a queuing services object
     and there are no handles available. Adjusting this value has no effect
     on BEA Tuxedo applications other than unnecessarily consuming shared
     memory resources."
        ::= { tuxTQspaceEntry 50 }
 
tuxTQspaceMaxOwners OBJECT-TYPE 
        SYNTAX  INTEGER 
        ACCESS  read-write
        STATUS  mandatory 
        DESCRIPTION 
     "This attribute specifies the number of additional BEA Engine
     authenticated users that may concurrently use Queuing Services
     resources. There is one owner record per user, regardless of the number
     of open handles for the user. When there are no open handles for a
     user, the owner record is made available for subsequent users. The
     system reserves owners equivalent to the number of actions so that each
     action may be initiated by a different owner. Beyond the
     system-reserved number of owners that may be concurrently using queuing
     services resources, the administrator may configure the system to
     accommodate additional owners beyond the reserve. An operation fails if
     a user attempts to open a handle when they currently do not have any
     open handles, and there are no owners available. Adjusting this value
     has no effect on BEA Tuxedo applications other than unnecessarily
     consuming shared memory resources."
        ::= { tuxTQspaceEntry 60 }
 
tuxTQspaceMaxTmpQueues OBJECT-TYPE 
        SYNTAX  INTEGER 
        ACCESS  read-write
        STATUS  mandatory 
        DESCRIPTION 
     "This attribute specifies the number of temporary queues that may be
     opened concurrently in the Queuing Services component of the BEA
     Engine. Temporary queues reduce the need for administrators to
     configure each queue used by an application. They are used by dynamic
     self-configuring applications. Messages enqueued to temporary queues
     are not persistent. When all handles to a temporary queue are closed,
     the temporary queue resources are made available for subsequent
     temporary queue creation. When the temporary queues are used by an
     application, the administrator must configure the system to accommodate
     the maximum number of temporary queues that will be active
     concurrently. An open operation fails if a user attempts to open a
     temporary queue and there are no temporary queue resources available.
     Adjusting this value has no effect on BEA Tuxedo applications other
     than unnecessarily consuming shared memory resources."
        ::= { tuxTQspaceEntry 70 }
 
tuxTQspaceMaxCursors OBJECT-TYPE 
        SYNTAX  INTEGER 
        ACCESS  read-write
        STATUS  mandatory 
        DESCRIPTION 
     "This attribute specifies the number of cursors that users of that the
     Queuing Services component of the BEA Engine may use concurrently.
     Cursors are used to navigate a queue. When a cursor is destroyed, the
     cursor resources are made available for subsequent cursor creation
     operations. When the cursors are used by an application, the
     administrator must configure the system to accommodate the maximum
     number of cursors that will be allocated concurrently. An operation
     fails if a user attempts to create a cursor and there are no cursor
     resources available. BEA Tuxedo applications need not adjust this
     value. Adjusting this value has no effect on BEA Tuxedo applications
     other than unnecessarily consuming shared memory resources."
        ::= { tuxTQspaceEntry 80 }
 
tuxTQspaceMemNonPersist OBJECT-TYPE 
        SYNTAX  DisplayString 
        ACCESS  read-write
        STATUS  mandatory 
        DESCRIPTION 
     "This attribute specifies the size of the area reserved in shared memory
     to hold non-persistent messages for all queues in the queue space. The
     memory size may be specified in bytes (b) or blocks (B) (the size of a
     block, in this context, is equivalent to the size of a disk block). The
     [Bb] suffix is optional and, if not specified, the default is blocks.
     Note that the number of bytes requested may be rounded up to the next
     internal data size. When read, the value is always the actual amount of
     memory allocated in bytes (b).

     All non-persistent messages in the specified queue space are
     permanently lost when this variable is successfully changed.

     If this variable for a queue space is zero (0) for a queue space, no
     space is reserved for non-persistent messages. In this case, any
     attempt to enqueue a non-persistent message fails. This type of failure
     results, for example, when no delivery quality of service has been
     specified for a message and the tuxTAppQDefDeliveryPolicy object of the
     tuxTAppQTbl group for the target queue has been set to NONPERSIST. For
     non-persistent delivery, if the memory area is exhausted or fragmented
     such that a message cannot be enqueued, the enqueuing operation fails,
     even if there is sufficient persistent storage for the message.
     Similarly, if the persistent storage area is exhausted or fragmented
     such that a message cannot be enqueued, the enqueuing operation fails,
     even if there is sufficient non-persistent storage for the message."
        ::= { tuxTQspaceEntry 90 }
 
tuxTQspaceMemFilters OBJECT-TYPE 
        SYNTAX  INTEGER 
        ACCESS  read-write
        STATUS  mandatory 
        DESCRIPTION 
     "This attribute specifies the size of the memory area to reserve in
     shared memory to hold the compiled representation of user defined
     filters. The memory size is specified in bytes. Filters are used by the
     Queuing Services component of the BEA Engine for message selection in
     dequeuing and cursor operations. Filters may be specified using various
     grammars but are compiled into an engine normal form and stored in
     shared memory. Filters are referenced by a handle returned when they
     are compiled. When a filter is destroyed, the memory used by the filter
     is made available for subsequent compiled filters. When the filters are
     defined by an application, the administrator must configure the system
     to accommodate the maximum number of filters that will be concurrently
     compiled. An operation fails if a user attempts to create a new filter
     and there is not enough memory allocated for the compiled version of
     the filter. Adjusting this value has no effect on BEA Tuxedo
     applications other than unnecessarily consuming shared memory
     resources."
        ::= { tuxTQspaceEntry 100 }
 
tuxTQspaceMemOverFlow OBJECT-TYPE 
        SYNTAX  INTEGER 
        ACCESS  read-write
        STATUS  mandatory 
        DESCRIPTION 
     "This attribute specifies the size of the memory area to reserve in
     shared memory to accommodate peek load situations where some or all of
     the allocated shared memory resources are exhausted. The memory size is
     specified in bytes. Additional objects are allocated from this
     additional memory on a first-come-first-served basis. When an object
     created in the additional memory is closed or destroyed, the memory is
     released for subsequent overflow situations. This additional memory
     space may yield more objects than the configured number, but there is
     no guarantee that additional memory is available for any particular
     object at any given point in time. Currently, only actions, handles,
     cursors, owners, temporary queues, timers, and filters use the overflow
     memory."
        ::= { tuxTQspaceEntry 110 }
 
tuxTQspaceMemSystemReserved OBJECT-TYPE 
        SYNTAX  INTEGER 
        ACCESS  read-only
        STATUS  mandatory 
        DESCRIPTION 
     "This attribute specifies the total amount of memory (in bytes) reserved
     from shared memory for queuing services system use."
        ::= { tuxTQspaceEntry 120 }
 
tuxTQspaceMemTotalAllocated OBJECT-TYPE 
        SYNTAX  INTEGER 
        ACCESS  read-only
        STATUS  mandatory 
        DESCRIPTION 
     "This attribute specifies the total amount of memory (in bytes)
     allocated from shared for all queuing services objects."
        ::= { tuxTQspaceEntry 130 }
 
tuxTQspaceCurActions OBJECT-TYPE 
        SYNTAX  INTEGER 
        ACCESS  read-only
        STATUS  mandatory 
        DESCRIPTION 
     "This attribute specifies the current number of actions in use in the
     queue space. This number can be determined if the queue space is OPEn
     or ACTive, or if the queue space is newly created. If none of the
     conditions apply, the value -1 is returned."
        ::= { tuxTQspaceEntry 140 }
 
tuxTQspaceCurHandles OBJECT-TYPE 
        SYNTAX  INTEGER 
        ACCESS  read-only
        STATUS  mandatory 
        DESCRIPTION 
     "This attribute specifies the current number of cursors in use in the
     queue space. This number can be determined if the queue space is OPEn
     or ACTive, or if the queue space is newly created. If none of the
     conditions apply, the value -1 is returned."
        ::= { tuxTQspaceEntry 150 }
 
tuxTQspaceCurOwners OBJECT-TYPE 
        SYNTAX  INTEGER 
        ACCESS  read-only
        STATUS  mandatory 
        DESCRIPTION 
     "This attribute specifies the current number of owners in use in the
     queue space. This number can be determined if the queue space is OPEn
     or ACTive, or if the queue space is newly created. If none of the
     conditions apply, the value -1 is returned."
        ::= { tuxTQspaceEntry 160 }
 
tuxTQspaceCurTmpQueues OBJECT-TYPE 
        SYNTAX  INTEGER 
        ACCESS  read-only
        STATUS  mandatory 
        DESCRIPTION 
     "This attribute specifies the current number of temporary queues in use
     in the queue space. This number can be determined if the queue space is
     OPEn or ACTive, or if the queue space is newly created. If none of the
     conditions apply, the value -1 is returned."
        ::= { tuxTQspaceEntry 170 }
 
tuxTQspaceCurCursors OBJECT-TYPE 
        SYNTAX  INTEGER 
        ACCESS  read-only
        STATUS  mandatory 
        DESCRIPTION 
     "This attribute specifies the current number of cursors in use in the
     queue space. This number can be determined if the queue space is OPEn
     or ACTive, or if the queue space is newly created. If none of the
     conditions apply, the value -1 is returned."
        ::= { tuxTQspaceEntry 180 }
 
tuxTQspaceCurMemNonPersist OBJECT-TYPE 
        SYNTAX  INTEGER 
        ACCESS  read-only
        STATUS  mandatory 
        DESCRIPTION 
     "The current amount of memory in bytes consumed by non-persistent
     messages in the queue space. This number can be determined if the queue
     space is OPEn or ACTive, or if the queue space is newly created. If
     none of the conditions apply, the value -1 is returned."
        ::= { tuxTQspaceEntry 190 }
 
tuxTQspaceCurMemFilters OBJECT-TYPE 
        SYNTAX  INTEGER 
        ACCESS  read-only
        STATUS  mandatory 
        DESCRIPTION 
     "This attribute specifies the current number of bytes in use for filters
     in the queue space. This number can be determined if the queue space is
     OPEn or ACTive, or if the queue space is newly created. If none of the
     conditions apply, the value -1 is returned."
        ::= { tuxTQspaceEntry 200 }
 
tuxTQspaceCurMemOverFlow OBJECT-TYPE 
        SYNTAX  INTEGER 
        ACCESS  read-only
        STATUS  mandatory 
        DESCRIPTION 
     "This attribute specifies the current number of bytes in use of the
     overflow memory in the queue space. This number can be determined if
     the queue space is OPEn or ACTive, or if the queue space is newly
     created. If none of the conditions apply, the value -1 is returned."
        ::= { tuxTQspaceEntry 210 }
 
tuxTQspaceHwActions OBJECT-TYPE 
        SYNTAX  INTEGER (0..100)
        ACCESS  read-only
        STATUS  mandatory 
        DESCRIPTION 
     "This attribute specifies the highest number of concurrent actions
     reached in the queue space since the queue space was last opened. The
     number is reset to 0 when the queue space state is set to CLEaning."
        ::= { tuxTQspaceEntry 220 }
 
tuxTQspaceHwHandles OBJECT-TYPE 
        SYNTAX  INTEGER 
        ACCESS  read-only
        STATUS  mandatory 
        DESCRIPTION 
     "This attribute specifies the highest number of concurrent handles
     opened in the queue space since the queue space was last opened. The
     number is reset to 0 when the queue space state is set to CLEaning."
        ::= { tuxTQspaceEntry 230 }
 
tuxTQspaceHwOwners OBJECT-TYPE 
        SYNTAX  INTEGER 
        ACCESS  read-only
        STATUS  mandatory 
        DESCRIPTION 
     "This attribute specifies the highest number of concurrent owners
     reached in the queue space since the queue space was last opened. The
     number is reset to 0 when the queue space state is set to CLEaning."
        ::= { tuxTQspaceEntry 240 }
 
tuxTQspaceHwTmpQueues OBJECT-TYPE 
        SYNTAX  INTEGER 
        ACCESS  read-only
        STATUS  mandatory 
        DESCRIPTION 
     "This attribute specifies the highest number of concurrent temporary
     queues opened in the queue space since the queue space was last opened.
     The number is reset to 0 when the queue space state is set to CLEaning."
        ::= { tuxTQspaceEntry 250 }
 
tuxTQspaceHwCursors OBJECT-TYPE 
        SYNTAX  INTEGER 
        ACCESS  read-only
        STATUS  mandatory 
        DESCRIPTION 
     "This attribute specifies the highest number of concurrent cursors
     created in the queue space since the queue space was last opened. The
     number is reset to 0 when the queue space state is set to CLEaning."
        ::= { tuxTQspaceEntry 260 }
 
tuxTQspaceHwMemNonPersist OBJECT-TYPE 
        SYNTAX  INTEGER 
        ACCESS  read-only
        STATUS  mandatory 
        DESCRIPTION 
     "The largest amount of memory in bytes consumed by non-persistent
     messages since the queue space was last opened. The number is reset to
     0 when the queue space state is set to CLEaning."
        ::= { tuxTQspaceEntry 270 }
 
tuxTQspaceHwMemFilters OBJECT-TYPE 
        SYNTAX  INTEGER 
        ACCESS  read-only
        STATUS  mandatory 
        DESCRIPTION 
     "This attribute specifies the highest number of bytes used for filters
     in the queue space since the queue space was last opened. The number is
     reset to 0 when the queue space state is set to CLEaning."
        ::= { tuxTQspaceEntry 280 }
 
tuxTQspaceHwMemOverFlow OBJECT-TYPE 
        SYNTAX  INTEGER 
        ACCESS  read-only
        STATUS  mandatory 
        DESCRIPTION 
     "This attribute specifies the highest number of bytes used in the
     overflow memory in the queue space since the queue space was last
     opened. The number is reset to 0 when the queue space state is set to
     CLEaning."
        ::= { tuxTQspaceEntry 290 }
 
-- Added : END-JANUS-NS-TUXEDO7.1-041400

--***************************************************************************
--   tuxTAppQtrans group
--   This represents runtime attributes of transactions associated with 
--   application queue spaces.
--***************************************************************************

tuxTQtransTbl OBJECT-TYPE
        SYNTAX  SEQUENCE OF TuxTQtransEntry
        ACCESS  not-accessible
        STATUS  mandatory
        DESCRIPTION
                  "This table contains info about  transactions associated 
		   with application queues. " 
        ::= { tuxTAppQ 4 }

tuxTQtransEntry OBJECT-TYPE
        SYNTAX TuxTQtransEntry
        ACCESS  not-accessible
        STATUS  mandatory
        DESCRIPTION
                  " A row in tuxTQtransTbl. 
		NOTE 1:
  		    The values returned by this MIB are controlled by 
		    tuxTAppQctrl. Refer to the description of the above group 
		    for details.

		NOTE 2:
		       All objects in this MIB group are local attributes i.e.
		       values for these objects correspond to the local host
		       only, where the TUXEDO agent is running. So the user needs
		       to run an instance of the TUXEDO agent on every node for
		       which these values are of interest."
        INDEX { tuxTQtransGrpNo , tuxTQtransIndx1 , tuxTQtransIndx2 , tuxTQtransIndx3 , tuxTQtransIndx4 , tuxTQtransIndx5 }
        ::= { tuxTQtransTbl 1 }

TuxTQtransEntry ::= SEQUENCE {
   tuxTQtransXid
        DisplayString,
   tuxTQtransIndx1
        INTEGER,
   tuxTQtransIndx2
        INTEGER,
   tuxTQtransIndx3
        INTEGER,
   tuxTQtransIndx4
        INTEGER,
   tuxTQtransIndx5
        INTEGER,
   tuxTQtransGrpNo
        INTEGER,
   tuxTQtranSpaceName
        DisplayString,
   tuxTQtransQmConfig
        DisplayString,
   tuxTQtransLmid
        DisplayString,
   tuxTQtransState
        INTEGER
   }

tuxTQtransXid OBJECT-TYPE
        SYNTAX 	DisplayString (SIZE(1..78))
        ACCESS  read-only
        STATUS  mandatory
        DESCRIPTION  
                  " Transaction identifier as returned  by  tx_info(3)  and
          	    mapped  to  a  string representation.  The data in this
          	    field should not be interpreted directly  by  the  user
          	    except for equality comparison. " 
        ::= { tuxTQtransEntry 1 }

tuxTQtransIndx1 OBJECT-TYPE
        SYNTAX  INTEGER
        ACCESS  read-only
        STATUS  mandatory
        DESCRIPTION
                  " An integer index for tuxTQtransTbl. This should not be 
		    interpreted by the user. It is used only for uniquely 
		    identifying a particular row in this table by the comb-
		    ination of Indx1 through Indx5. "
        ::= { tuxTQtransEntry 2 }
 
tuxTQtransIndx2 OBJECT-TYPE 
        SYNTAX  INTEGER
        ACCESS  read-only
        STATUS  mandatory 
        DESCRIPTION 
                  " An integer index for tuxTQtransTbl. This should not be 
                    interpreted by the user. It is used only for uniquely 
                    identifying a particular row in this table by the comb-
                    ination of Indx1 through Indx5. "
        ::= { tuxTQtransEntry 3 } 
  
tuxTQtransIndx3 OBJECT-TYPE 
        SYNTAX  INTEGER
        ACCESS  read-only
        STATUS  mandatory 
        DESCRIPTION 
                  " An integer index for tuxTQtransTbl. This should not be 
                    interpreted by the user. It is used only for uniquely 
                    identifying a particular row in this table by the comb-
                    ination of Indx1 through Indx5. "
        ::= { tuxTQtransEntry 4 } 
  
tuxTQtransIndx4 OBJECT-TYPE 
        SYNTAX  INTEGER
        ACCESS  read-only
        STATUS  mandatory 
        DESCRIPTION 
                  " An integer index for tuxTQtransTbl. This should not be 
                    interpreted by the user. It is used only for uniquely 
                    identifying a particular row in this table by the comb-
                    ination of Indx1 through Indx5. "
        ::= { tuxTQtransEntry 5 } 
  
tuxTQtransIndx5 OBJECT-TYPE 
        SYNTAX  INTEGER
        ACCESS  read-only
        STATUS  mandatory 
        DESCRIPTION 
                  " An integer index for tuxTQtransTbl. This should not be 
                    interpreted by the user. It is used only for uniquely 
                    identifying a particular row in this table by the comb-
                    ination of Indx1 through Indx5. "
        ::= { tuxTQtransEntry 6 } 
  
tuxTQtransGrpNo OBJECT-TYPE 
        SYNTAX  INTEGER
        ACCESS  read-only
        STATUS  mandatory 
        DESCRIPTION 
                  " Group number of any server group for which the queue space
                    concerning this transaction is a resource manager, in other 		    words that group's openinfo string tuxTgroupOpenInfo 
		    contains the device name and queue space name for the queue 		    space concerning this transaction. "
        ::= { tuxTQtransEntry 7 } 
  
tuxTQtranSpaceName OBJECT-TYPE  
        SYNTAX 	DisplayString (SIZE(1..15))
        ACCESS  read-only
        STATUS  mandatory 
        DESCRIPTION     
                  " Name of the application queue space associated with the
          	    transaction. "
        ::= { tuxTQtransEntry 8 } 
  
tuxTQtransQmConfig OBJECT-TYPE 
        SYNTAX 	DisplayString (SIZE(1..256))
        ACCESS  read-only
        STATUS  mandatory 
        DESCRIPTION     
                  " Absolute pathname of  the  file  or  device  where  the
          	    application queue space is located. " 
        ::= { tuxTQtransEntry 9 } 
  
tuxTQtransLmid OBJECT-TYPE 
        SYNTAX 	DisplayString (SIZE(1..30))
        ACCESS  read-only
        STATUS  mandatory 
        DESCRIPTION     
                  " Identifier of the logical machine where the application
          	    queue space is located. "
        ::= { tuxTQtransEntry 10 } 
  
tuxTQtransState OBJECT-TYPE 
        SYNTAX INTEGER {
		active(1),
		abort-only(2),
		aborted(3),
		com-called(4),
		ready(5),
		decided(6),
		suspended(7),
		habort(8),
		hcommit(9)
		}
        ACCESS  read-write
        STATUS  mandatory 
        DESCRIPTION     
                  "
          GET: A  GET  operation  retrieves  runtime  information
               about the selected  transactions.   The  following
               list  describes the meaning of the tuxTQtransState attri-
               bute  returned  in  response  to  a  GET  request.
               States  not  listed  will  not  be  returned.

               active(1)    The transaction is active.

               abort-only(2)    
			    The transaction has  been  identified
                            for rollback.

               aborted(3)   The transaction has  been  identified
                            for  rollback  and  rollback has been
                            initiated.

               com-called(4)
			    The initiator of the transaction  has
                            called   tpcommit(3)  and  the  first
                            phase of two-phase commit has begun.
 
               ready(5)     All of the  participating  groups  on
                            the  retrieval site have successfully
                            completed the  first  phase  of  two-
                            phase commit and are ready to be com-
                            mitted.
               decided(6)   The second  phase  of  the  two-phase
                            commit has begun.
               suspended(7) The initiator of the transaction  has
                            suspended  processing on the transac-
                            tion.

          SET: {HABort|HCOmmit}
               A SET operation updates the state of the  selected
               transactions.   The  following  list describes the
               meaning of the tuxTQtransState attribute  returned  by  a
               SET request.  States not listed can not be set.

               habort(8)    Heuristically abort the  transaction.
                            Successful  return  leaves the object
                            in the habort(8) state.
               hcommit(9)   Heuristically commit the transaction.
                            Successful  return  leaves the object
                            in the hcommit(9) state. "
        ::= { tuxTQtransEntry 11 } 

  
--***************************************************************************
-- tuxTBridge group
-- This group represents runtime attributes  pertaining
--   to connectivity between logical machines making up an appli-
--   cation.  These attribute values represent connection  status
--   and statistics.
--***************************************************************************

tuxTBridgeTbl OBJECT-TYPE
        SYNTAX  SEQUENCE OF TuxTBridgeEntry
        ACCESS  not-accessible
        STATUS  mandatory
        DESCRIPTION
                  "This table contains info about connectivity between 
		   logical machines making up an application. " 
        ::= { tuxTBridge 1 }

tuxTBridgeEntry OBJECT-TYPE
        SYNTAX TuxTBridgeEntry
        ACCESS  not-accessible
        STATUS  mandatory
        DESCRIPTION
                  " A row in tuxTBridgeTbl.

		NOTE: All objects in this MIB group are local attributes i.e.
		      values for these objects correspond to the local host
		      only, where the TUXEDO agent is running. So the user needs
		      to run an instance of the TUXEDO agent on every node for
		      which these values are of interest.
		NOTE: In Tuxedo 6.4, SET requests are allowed only for the 
		      'DEFAULTNET' network group, so all SET requests should 
		      use 0 for tuxTBridgeNetworkGrpNo in the SNMP index. "
        INDEX { tuxTBridgeLmid , tuxTBridgeNetworkGrpNo }
        ::= { tuxTBridgeTbl 1 }

TuxTBridgeEntry ::= SEQUENCE {
   tuxTBridgeLmid
        DisplayString,
   tuxTBridgeState
        INTEGER,
   tuxTBridgeCurTime
        INTEGER,
   tuxTBridgeConTime
        INTEGER,
   tuxTBridgeSuspTime
        INTEGER,
   tuxTBridgeRcvdByte
	INTEGER,
   tuxTBridgeSentByte
	INTEGER,
   tuxTBridgeRcvdNum
	INTEGER,
   tuxTBridgeSentNum
	INTEGER,
   tuxTBridgeFlowCnt
	INTEGER,
   tuxTBridgeCurEncryptBits
	INTEGER,
   tuxTBridgeNetworkGrpNo
	INTEGER,
   tuxTBridgeNetworkGrpName
	DisplayString
   }

tuxTBridgeLmid OBJECT-TYPE 
        SYNTAX DisplayString (SIZE(1..61)) 
        ACCESS  read-only
        STATUS  mandatory    
        DESCRIPTION 
                  " Source logical machine identifier (LMID1) and  destina-
          	    tion  logical  machine  identifier  (LMID2) for network
          	    connection. Format: LMID1[,LMID2]"
        ::= { tuxTBridgeEntry 1 } 
 
tuxTBridgeState OBJECT-TYPE 
        SYNTAX	INTEGER {
		active(1),
		inactive(2),
		suspended(3),
		pending(4)
		} 
        ACCESS  read-write
        STATUS  mandatory     
        DESCRIPTION  
                  " 
          GET:
               A GET operation will retrieve runtime  information
               for  the  selected  tuxTbridgeTbl instance(s).  A 
	       tuxTbridgeLmid object value  with  only  one  
	       logical  machine identifier  matches  all  active  
	       connections from that machine to other machines in  
	       the  application.   In this  case,  each retrieved 
	       record will contain an expanded tuxTbridgeLmid attribute 
	       value with the destination LMID filled in. The following 
	       states indicate  the  meaning of a tuxTbridgeState 
	       returned in response to a GET request.  States not listed 
		will not be returned.

               active(1)    The  connection  is  established  and
                            active.

               inactive(2)  The  connection  is  inactive.   This
                            state is only returned when status is
                            requested on a particular connection,
                            that  is, both LMIDs specified in the
                            tuxTbridgeLmid attribute and the source 
			    logical machine is reachable.

               suspended(3) An established  connection  was  ter-
                            minated  due  to  an error condition,
                            and reconnection has  been  suspended
                            for at least the amount of time indi-
                            cated in  the  tuxTbridgeSuspTime object
                            value.

	       pending(4)   An asynchronous connection has been requested, but 
			    has not yet completed. The final outcome of the 
			    connection request has not been determined. 
			    SUPPORT: Tuxedo 6.4 and later only.
          SET: 
               A SET operation will  update  runtime  information
               for  the  selected tuxTbridgeLmid object.  The following
               states indicate the meaning of a tuxTbridgeState set in a
               SET request.  States not listed may not be set.

               active(1)    Tuxedo Versions 6.3 and earlier:
			    -------------------------------
			    Activate the tuxTbridgeTbl instance by
                            establishing a connection between the
                            indicated logical  machines.  This
                            operation will fail if only one logi-
                            cal machine is specified,  if  either
                            of the two machines is not active, or
                            if the source logical machine is  not
                            reachable.   State  change allowed in
                            the inactive(2) and suspended(3) states.
                            Successful  return  leaves the object
                            in the active(1) state.
			
			    Tuxedo version 6.4 and later:
			    ----------------------------
			    Activate the tuxTBridgeTbl instance by establishing
			    an asynchronous connection between the indicated
			    logical machines. This operation will fail if
			    only one machine is specified, if either of the
			    machines is not active, or if the source machine
			    is not reachable. When in the pending(4) state,
			    the success or failure of the connection has not
			    yet been determined. However, the BRIDGE may conti-
			    nue to process other events and data while the 
			    connection is outstanding. This state change is
			    allowed in the inactive(2) and suspended(3) states.
			    Successful return leaves the instance in active(1)
			    or pending(4) state.

               inactive(2)  Deactivate  the  tuxTbridgeTbl instance by
                            closing  the  connection  between the
                            indicated  logical  machines.    This
                            operation will fail if only one logi-
                            cal machine is specified  or  if  the
                            two   machines   are  not  connected.
                            State change allowed only when in the
                            active(1) state.    Successful  return
                            leaves the  object  in the inactiv(2)
                            state.

               suspended(3) Suspend the tuxTbridgeTbl instance by  clos-
                            ing  the connection between the indi-
                            cated logical machines and by setting
                            the  tuxTbridgeSuspTime parameter  as indi-
                            cated.   State  change  allowed  only
                            when in the active(1) state.  Successful
                            return  leaves  the  object  in   the
                            suspended(3) state.

                            Limitation:  Note  that   since   the
                            statistics   reported  are  from  the
                            viewpoint  of  the   source   logical
                            machine,  resetting  those statistics
                            will cause them to  be  out  of  sync
                            with  the  statistics reported by the
                            destination logical machine  for  the
                            same connection. 
	      pending(4)    Activate the tuxTBridgeTbl instance by establishing 
			    a asynchronous connection between the indicated 
			    logical machines. This operation will fail if only 
			    one logical machine is specified, if eitherof the 
			    two machines is not active, or if the source logical
			    machine is not reachable. When in the pending(4)
			    state, the success or failure of the connection 
			    request has not yet been determined. However, the 
			    BRIDGE may continue to process other events and 
			    data while the connection is outstanding. State 
			    change allowed in inactive(2) and suspended(3) 
			    states. Successful return leaves the instance in 
			    the pending(4) state.
			    SUPPORT: Tuxedo 6.4 and later only. "
        ::= { tuxTBridgeEntry 2 }  
  
tuxTBridgeCurTime OBJECT-TYPE 
        SYNTAX	INTEGER 
        ACCESS  read-only
        STATUS  mandatory     
        DESCRIPTION  
                  " Current time, in seconds, since 00:00:00  UTC,  January
          	    1,  1970,  as  returned  by  the time(2) system call on
          	    tuxTbridgeLmid.  This attribute can be used  to  com-
          	    pute elapsed time from the following attribute values. "
        ::= { tuxTBridgeEntry 3 }  
   
tuxTBridgeConTime OBJECT-TYPE  
        SYNTAX	INTEGER 
        ACCESS  read-only
        STATUS  mandatory      
        DESCRIPTION   
                  " Time, in seconds, that this connection has been active. "
        ::= { tuxTBridgeEntry 4 }   
   
tuxTBridgeSuspTime OBJECT-TYPE  
        SYNTAX	INTEGER 
        ACCESS  read-write
        STATUS  mandatory      
        DESCRIPTION   
                  " Time, in seconds, remaining in the suspension  of  this
          	    connection.   After this amount of time, the connection
          	    will automatically change to a tuxTBridgeState of inactive 
		    and may be activated by normal application traffic. "
        ::= { tuxTBridgeEntry 5 }   
   
tuxTBridgeRcvdByte OBJECT-TYPE  
        SYNTAX	INTEGER 
        ACCESS  read-only
        STATUS  mandatory      
        DESCRIPTION   
                  " Number of  bytes  sent  from  the  destination  logical
          	    machine to the source logical machine. "
        ::= { tuxTBridgeEntry 6 }   
   
tuxTBridgeSentByte OBJECT-TYPE  
        SYNTAX	INTEGER 
        ACCESS  read-only
        STATUS  mandatory      
        DESCRIPTION   
                  " Number of bytes sent from the source logical machine to
          	    the destination logical machine. "
        ::= { tuxTBridgeEntry 7 }   
   
tuxTBridgeRcvdNum OBJECT-TYPE  
        SYNTAX	INTEGER 
        ACCESS  read-only
        STATUS  mandatory      
        DESCRIPTION   
                  " Number of messages sent from  the  destination  logical
          	    machine to the source logical machine. "
        ::= { tuxTBridgeEntry 8 }   
   
tuxTBridgeSentNum OBJECT-TYPE
        SYNTAX  INTEGER 
        ACCESS  read-only
        STATUS  mandatory      
        DESCRIPTION  
                  " Number of messages sent from the source logical machine
          	    to the destination logical machine. "
        ::= { tuxTBridgeEntry 9 }

tuxTBridgeFlowCnt OBJECT-TYPE 
        SYNTAX  INTEGER 
        ACCESS  read-only
        STATUS  mandatory       
        DESCRIPTION   
                  " Number of times flow control has been encountered  over
          	    this connection. "
        ::= { tuxTBridgeEntry 10 } 
  
tuxTBridgeCurEncryptBits OBJECT-TYPE 
        SYNTAX  INTEGER {
		none(1),
		enc-40-bit(2),
		enc-128-bit(3),
		not-available(4)
		} 
        ACCESS  read-only
        STATUS  mandatory       
        DESCRIPTION   
                  " The current level of encryption for this link, this is neg-
		    otiated between the machines when the link is established.
		    The number specifies the encryption key length. 
		    SUPPORT: Tuxedo 6.4 and later only."
        ::= { tuxTBridgeEntry 11 } 
  
tuxTBridgeNetworkGrpNo OBJECT-TYPE 
        SYNTAX  INTEGER 
        ACCESS  read-only
        STATUS  mandatory       
        DESCRIPTION   
                  " Logical network group number. When both the source and 
		    destination tuxTBridgeLmid machine identifiers are in the 
		    same network group, tuxTBridgeTbl will present all 
		    instances of related fields per network group.
		    SUPPORT: Tuxedo 6.4 and later only."
        ::= { tuxTBridgeEntry 12 } 
  
tuxTBridgeNetworkGrpName OBJECT-TYPE 
        SYNTAX  DisplayString
        ACCESS  read-only
        STATUS  mandatory       
        DESCRIPTION   
                  " Logical network group name.
		    SUPPORT: Tuxedo 6.4 and later only."
        ::= { tuxTBridgeEntry 13 } 
  
-- ************************************************************************** 
-- tuxTclient group
-- This group represents runtime attributes  of  active
--   clients within an application.  These attribute values iden-
--   tify and track the activity  of  clients  within  a  running
--   application.
-- ************************************************************************** 

tuxTclientTbl OBJECT-TYPE
        SYNTAX  SEQUENCE OF TuxTclientEntry
        ACCESS  not-accessible 
        STATUS  mandatory
        DESCRIPTION
                  " This table contains runtime attributes  of  active 
	    	    clients within an application. "
        ::= { tuxTclient 1 }

tuxTclientEntry OBJECT-TYPE 
        SYNTAX  TuxTclientEntry 
        ACCESS  not-accessible 
        STATUS  mandatory    
        DESCRIPTION 
                  " A row in tuxTclientTbl.

		NOTE:  All objects in this MIB group are local attributes i.e.
		       values for these objects correspond to the local host
		       only, where the TUXEDO agent is running. So the user needs
		       to run an instance of the TUXEDO agent on every node for
		       which these values are of interest."
	INDEX { tuxTclientBirthTime,tuxTclientMachineId,tuxTclientReg }
        ::= { tuxTclientTbl 1 } 

TuxTclientEntry ::= SEQUENCE {
	tuxTclientState
		INTEGER,
	tuxTclientBirthTime
		INTEGER,
	tuxTclientMachineId
		INTEGER,
	tuxTclientReg
		INTEGER,
	tuxTclientClntName
		DisplayString,
	tuxTclientIdleTime
		INTEGER,
	tuxTclientPid
		INTEGER,
	tuxTclientSrvGrp
		DisplayString,
	tuxTclientUsrName
		DisplayString,
	tuxTclientWsc
		INTEGER,
	tuxTclientWsh
		INTEGER,
	tuxTclientWshClientId
		DisplayString,
	tuxTclientRelease
		INTEGER,
	tuxTclientWsProto
		INTEGER,
	tuxTclientNumConv
		INTEGER,
	tuxTclientNumDeque
		INTEGER,
	tuxTclientNumEnque
		INTEGER,
	tuxTclientNumPost
		INTEGER,
	tuxTclientNumReq
		INTEGER,
	tuxTclientNumSubscribe
		INTEGER,
	tuxTclientNumTran
		INTEGER,
	tuxTclientNumTranAbt
		INTEGER,
	tuxTclientNumTranCmt
		INTEGER,
	tuxTclientCmtRet
		INTEGER,
	tuxTclientCurConv
		INTEGER,
	tuxTclientCurReq
		INTEGER,
	tuxTclientCurTime
		INTEGER,
	tuxTclientLastGrp
		INTEGER,
	tuxTclientNaddr
		DisplayString,
	tuxTclientNotify
		INTEGER,
	tuxTclientNumUnSol
		INTEGER,
	tuxTclientRpid
		INTEGER,
	tuxTclientTimeLeft
		INTEGER,
	tuxTclientTimeStart
		INTEGER,
	tuxTclientTranLev
		INTEGER,
	tuxTclientId
		DisplayString,
	tuxTclientContextID
		INTEGER
	}	
 

tuxTclientState OBJECT-TYPE
        SYNTAX  INTEGER {
		active(1),
		suspended(2),
		dead(3)
		}
        ACCESS  read-write
        STATUS  mandatory
        DESCRIPTION
                  " 
          GET:
               A GET operation will retrieve runtime  information
               for  the  selected  tuxTclientTbl instance(s).  Note that
               client information is kept in local bulletin board
               tables  only.  Therefore, for maximum performance,
               inquiries on client status  should  be  restricted
               using key fields as much as possible.  The follow-
               ing states indicate  the  meaning  of  a  tuxTclientState
               returned in response to a GET request.  States not
               listed will not be returned.

               active(1)    tuxTclient instance active.  This is  not
                            an  indication  of whether the client
                            is idle  or  busy.   A  non  0  value
                            retrieved  for  either the tuxTclientCurConv
                            attribute or the tuxTclientCurReq  attribute
                            indicates a busy client.

               suspended(2) tuxTclient instance active and  suspended
                            from  making further service requests
                            (tpcall(3) or  tpacall(3))  and  from
                            initiating    further   conversations
                            (tpconnect(3)).   See  SET  suspended(2)
                            below  for  details.

               dead(3)      tuxTclient instance identified as  active
                            in  the  bulletin board but currently
                            not running due to an abnormal death.
                            This  state will exist only until the
                            BBL local to the client  notices  the
                            death  and  takes  action to clean up
                            the    client's    bulletin     board
                            resources.

          SET:
               A SET operation will  update  runtime  information
               for  the  selected tuxTclientTbl instance. The following
               states indicate the meaning of a tuxTclientState set in a
               SET request.  States not listed may not be set.

               active(1)    Activate a Suspended tuxTclientTbl instance.
                            State change allowed only when in the
                            suspended(2) state.   Successful  return
                            leaves   the  object  in  the  active(1)
                            state.

               suspended(2) Suspend the tuxTclient instance from mak-
                            ing  service  requests  (tpcall(3) or
                            tpacall(3)), initiating conversations
                            (tpconnect(3)),   beginning  transac-
                            tions (tpbegin(3)), and enqueuing new
                            requests   (tpenqueue(3)).    Clients
                            within a transaction will be  permit-
                            ted  to  make  these calls until they
                            abort or commit the current  transac-
                            tion,  at which time they will become
                            suspended.  Invocations of these rou-
                            tines  will  result  in  a  TPESYSTEM
                            error return and a system log message
                            being generated indicating the situa-
                            tion.  State change allowed only when
                            in   the  active(1) state.   Successful
                            return  leaves  the  object  in   the
                            suspended(2) state.

               dead(3)      Abortively  deactivate  the  tuxTclient 
                            instance.   State  change  allowed only
                            when  in  the  active(1) or suspended(2)
                            state.   The  recommended  method for
                            deactivating  clients  is  to   first
                            to suspend  them  and then to
                            abortively deactivate them by setting
                            the state to dead(3).  Successful return
                            leaves the object in the dead(3) state.

                            Limitation:   Workstation    handlers
                            (tuXTclientWsh == yes(1)) may not be set
                            to a state of dead(3).
                            The system may not be  able  to  kill
                            the client due to platform or signal-
                            ing restrictions.  In  this  case,  a
                            native client will be abortively ter-
                            minated at its next access  to  ATMI,
                            and a workstation client's connection
                            to a WSH will  be  preemptively  torn
                            down. " 
        ::= { tuxTclientEntry 1 }

tuxTclientBirthTime OBJECT-TYPE
        SYNTAX  INTEGER
        ACCESS  read-only
        STATUS  mandatory
        DESCRIPTION
                  " Client identifier.  The data in this field  should  not
          	    be  interpreted  directly  by  the  end user except for
          	    equality comparison. "
        ::= { tuxTclientEntry 2 }

tuxTclientMachineId OBJECT-TYPE
        SYNTAX  INTEGER
        ACCESS  read-only
        STATUS  mandatory
        DESCRIPTION
                  " Client identifier.  The data in this field  should  not
                    be  interpreted  directly  by  the  end user except for
                    equality comparison. "
        ::= { tuxTclientEntry 3 }
 
tuxTclientReg   OBJECT-TYPE
        SYNTAX  INTEGER
        ACCESS  read-only
        STATUS  mandatory
        DESCRIPTION
                  " Client identifier.  The data in this field  should  not
                    be  interpreted  directly  by  the  end user except for
                    equality comparison. "
        ::= { tuxTclientEntry 4 }
 
tuxTclientClntName OBJECT-TYPE
        SYNTAX  DisplayString (SIZE(0..30))
        ACCESS  read-only
        STATUS  mandatory
        DESCRIPTION
                  " Client name associated with client  at  tpinit(3)  time
          	    via the cltname element of the TPINIT structure. "
        ::= { tuxTclientEntry 5 }
 
tuxTclientIdleTime OBJECT-TYPE
        SYNTAX  INTEGER
        ACCESS  read-only
        STATUS  mandatory
        DESCRIPTION
                  "  Approximate amount of  time,  in  seconds,  since  
			this
          	     client  last  interacted  with  the  system via an ATMI
          	     call.  This value is  accurate  to  within  
		     tuxTdomainScanUnit
          	     (see  the tuxTdomain group) seconds.  When specified as a
          	     key field, a positive value indicates that all  clients
          	     with  idle  times of least the indicated value match, a
          	     negative value indicates that all clients with no  more
          	     than  the  indicated value match, and a 0 value matches
          	     all clients. "
        ::= { tuxTclientEntry 6 }
 
tuxTclientPid OBJECT-TYPE
        SYNTAX  INTEGER
        ACCESS  read-only
        STATUS  mandatory
        DESCRIPTION
                  " Process identifier of client.  Note that  for  worksta-
          	    tion clients, this identifier indicates the workstation
          	    handler through which the workstation  client  is  con-
          	    nected.   A  negative  number may be specified on a GET
          	    operation for the purpose of retrieving client informa-
          	    tion  for  the calling process.  If the calling process
          	    is not a client, then an error will be returned. "
        ::= { tuxTclientEntry 7 }
 
tuxTclientSrvGrp OBJECT-TYPE
        SYNTAX  DisplayString (SIZE(0..30))
        ACCESS  read-only
        STATUS  mandatory
        DESCRIPTION
                  " Server group with which the client is associated.  This
          	    information  is  set  via  the  grpname  element of the
          	    TPINIT structure at tpinit(3) time. "
        ::= { tuxTclientEntry 8 }
 
tuxTclientUsrName OBJECT-TYPE
        SYNTAX  DisplayString (SIZE(0..30))
        ACCESS  read-only
        STATUS  mandatory
        DESCRIPTION
                  " User name associated with client at tpinit(3) time  via
          	    the usrname element of the TPINIT structure. "
        ::= { tuxTclientEntry 9 }
 
tuxTclientWsc OBJECT-TYPE
        SYNTAX  INTEGER {
		yes(1),
		no(2)
		}
        ACCESS  read-only
        STATUS  mandatory
        DESCRIPTION
                  " If this attribute is set  to  yes(1), then  the 
		    indicated client is logged in to the application 
		    from a remote workstation. "
        ::= { tuxTclientEntry 10 }
 
tuxTclientWsh OBJECT-TYPE
        SYNTAX  INTEGER {
		yes(1),
		no(2)
		}
        ACCESS  read-only
        STATUS  mandatory
        DESCRIPTION
                  " Workstation handler.  If this attribute is set to  yes(1),
          	    then the indicated client is a workstation handler pro-
          	    cess. "
        ::= { tuxTclientEntry 11 }
 
tuxTclientWshClientId OBJECT-TYPE
        SYNTAX  DisplayString (SIZE(1..78))
        ACCESS  read-only
        STATUS  mandatory
        DESCRIPTION
                  " Client  identifier  for  the   associated   workstation
          	    handler  (WSH)  if  this client is a workstation client
          	    (tuxTclientWsc  ==  yes(1));  otherwise,  this  attribute  
		    will  be returned as a 0-length string. "
        ::= { tuxTclientEntry 12 }
 
tuxTclientRelease OBJECT-TYPE
        SYNTAX  INTEGER
        ACCESS  read-only
        STATUS  mandatory
        DESCRIPTION
                  " The TUXEDO System/T major protocol release  number  for
          	    the  machine  where the client is running.  This may be
          	    different from the TA_SWRELEASE for the  same  machine.
          	    Note that for /WS clients (tuxTclientWsc == yes(1)), this 
		    value may be different than the major release associated 
		    with the application  administered machine through which 
		    the /WS client accesses the application. "
        ::= { tuxTclientEntry 13 }
 
tuxTclientWsProto OBJECT-TYPE
        SYNTAX  INTEGER
        ACCESS  read-only
        STATUS  mandatory
        DESCRIPTION
                  " The TUXEDO System/T /WS protocol version number  for  a
          	    workstation  client.   This  value is changed with each
          	    update to the /WS protocol.  A value of 0  is  returned
          	    for this attribute when associated with non-/WS clients
          	    (tuxTclientWsc == no(2)). "
        ::= { tuxTclientEntry 14 }
 
tuxTclientNumConv OBJECT-TYPE
        SYNTAX  INTEGER
        ACCESS  read-only
        STATUS  mandatory
        DESCRIPTION
                  " Number of conversations initiated by  this  client  via
          	    tpconnect(3). "
        ::= { tuxTclientEntry 15 }
 
tuxTclientNumDeque OBJECT-TYPE
        SYNTAX  INTEGER
        ACCESS  read-only
        STATUS  mandatory
        DESCRIPTION
                  " Number of dequeue operations initiated by  this  client
          	    via tpdequeue(3). "
        ::= { tuxTclientEntry 16 }
 
tuxTclientNumEnque OBJECT-TYPE
        SYNTAX  INTEGER
        ACCESS  read-only
        STATUS  mandatory
        DESCRIPTION
                  "  Number of enqueue operations initiated by  this  client
          	     via tpenqueue(3). "
        ::= { tuxTclientEntry 17 }
 
tuxTclientNumPost OBJECT-TYPE
        SYNTAX  INTEGER
        ACCESS  read-only
        STATUS  mandatory
        DESCRIPTION
                  "  Number  of  postings  initiated  by  this  client   via
          	     tppost(3). "
        ::= { tuxTclientEntry 18 }
 
tuxTclientNumReq OBJECT-TYPE
        SYNTAX  INTEGER
        ACCESS  read-only
        STATUS  mandatory
        DESCRIPTION
                  " Number of requests made by this client via tpcall(3) or
          	    tpacall(3). "
        ::= { tuxTclientEntry 19 }

tuxTclientNumSubscribe OBJECT-TYPE
        SYNTAX  INTEGER
        ACCESS  read-only
        STATUS  mandatory
        DESCRIPTION
                  " Number of subscriptions made by this client via  tpsub-
          	    scribe(3). "
        ::= { tuxTclientEntry 20 }
 
tuxTclientNumTran OBJECT-TYPE
        SYNTAX  INTEGER
        ACCESS  read-only
        STATUS  mandatory
        DESCRIPTION
                  " Number of transactions begun by this client. "
        ::= { tuxTclientEntry 21 }
 
tuxTclientNumTranAbt OBJECT-TYPE
        SYNTAX  INTEGER
        ACCESS  read-only
        STATUS  mandatory
        DESCRIPTION
                  " Number of transactions aborted by this client. "
        ::= { tuxTclientEntry 22 }
 
tuxTclientNumTranCmt OBJECT-TYPE
        SYNTAX  INTEGER
        ACCESS  read-only
        STATUS  mandatory
        DESCRIPTION
                  "  Number of transactions committed by this client. " 
        ::= { tuxTclientEntry 23 }
 
 
tuxTclientCmtRet OBJECT-TYPE
        SYNTAX  INTEGER {
		complete(1),
		logged(2)
		}
        ACCESS  read-only
        STATUS  mandatory
        DESCRIPTION
                  " Setting of  the  TP_COMMIT_CONTROL  characteristic  for
          	    this  client.  See the description of the System/T ATMI
          	    function tpscmt(3) for details on this characteristic. "
        ::= { tuxTclientEntry 24 }
 
 
tuxTclientCurConv OBJECT-TYPE
        SYNTAX  INTEGER
        ACCESS  read-only
        STATUS  mandatory
        DESCRIPTION
                  " Number of conversations initiated by  this  client  via
          	    tpconnect(3) that are still active. "
        ::= { tuxTclientEntry 26 }
 
tuxTclientCurReq OBJECT-TYPE 
        SYNTAX  INTEGER 
        ACCESS  read-only
        STATUS  mandatory 
        DESCRIPTION   
                  " Number  of  requests  initiated  by  this  client   via
          	    tpcall(3) or tpacall(3) that are still active. "
        ::= { tuxTclientEntry 27 } 
  
tuxTclientCurTime OBJECT-TYPE 
        SYNTAX  INTEGER 
        ACCESS  read-only
        STATUS  mandatory 
        DESCRIPTION   
                  " Current time, in seconds, since 00:00:00  UTC,  
		    January 1,  1970,  as  returned  by  the time(2) system 
		    call on the local host.  This attribute can be used  
		    to  compute elapsed time from the tuxTclientTimeStart 
		    attribute value.  "
        ::= { tuxTclientEntry 28 } 
  
tuxTclientLastGrp OBJECT-TYPE 
        SYNTAX  INTEGER 
        ACCESS  read-only
        STATUS  mandatory 
        DESCRIPTION   
                  " Server group number of the last service  request  made 
		    or conversation initiated from this client. "
        ::= { tuxTclientEntry 29 } 
  
tuxTclientNaddr OBJECT-TYPE 
        SYNTAX  DisplayString (SIZE(1..256)) 
        ACCESS  read-only
        STATUS  mandatory 
        DESCRIPTION   
                  " For workstation clients, this attribute  indicates  the
          	    network  address of the client.  Network addresses with
          	    unprintable characters will be converted to the `0x...'
          	    network  address  format  as described in the 
		    tuxTmachineNaddr attribute.    Non-workstation
          	    clients  will  have  a  0-length string associated with
          	    them for this attribute value.
	    
          	    Limitation: The ability of the system to  provide  this
          	    information  is determined by the transport provider in
          	    use.  In some cases, workstation clients may  not  have
          	    addresses associated with them if the provider does not
          	    make this information available. "
        ::= { tuxTclientEntry 30 } 
  
tuxTclientNotify OBJECT-TYPE 
        SYNTAX  INTEGER  {
		dipin(1),
		signal(2),
		ignore(3)
		}
        ACCESS  read-only
        STATUS  mandatory 
        DESCRIPTION   
                  " Setting of the  notification  characteristic  for  this
          	    client.   See  the  tuxTdomain  group description of this
          	    attribute for more details. "
        ::= { tuxTclientEntry 31 } 
  
tuxTclientNumUnSol OBJECT-TYPE 
        SYNTAX  INTEGER 
        ACCESS  read-only
        STATUS  mandatory 
        DESCRIPTION   
                  " Number of unsolicited messages queued for  this  client
          	    awaiting processing. "
        ::= { tuxTclientEntry 32 } 
  
tuxTclientRpid OBJECT-TYPE 
        SYNTAX  INTEGER 
        ACCESS  read-only
        STATUS  mandatory 
        DESCRIPTION   
                  " UNIX System message queue identifier for  the  client's
          	    reply queue.
          	    Limitation: This is a UNIX  System  specific  attribute
          	    that  may  not be returned if the platform on which the
          	    application is being run is not UNIX-based. "
        ::= { tuxTclientEntry 33 } 
  
tuxTclientTimeLeft OBJECT-TYPE 
        SYNTAX  INTEGER 
        ACCESS  read-only
        STATUS  mandatory 
        DESCRIPTION   
                  " Time left, in seconds, for this client to receive the
          	   reply  for which it is currently waiting before it will
          	   timeout.  This timeout may be a  transactional  timeout
          	   or a blocking timeout. "
        ::= { tuxTclientEntry 34 } 
  
tuxTclientTimeStart OBJECT-TYPE 
        SYNTAX  INTEGER 
        ACCESS  read-only
        STATUS  mandatory 
        DESCRIPTION   
                  " Time, in seconds, since 00:00:00 UTC, January 1,  
		    1970, as   returned   by   the   time(2)   system   
		    call   on local host, since the client joined 
		    the  application. "
        ::= { tuxTclientEntry 36 } 
  
tuxTclientTranLev OBJECT-TYPE 
        SYNTAX  INTEGER 
        ACCESS  read-only
        STATUS  mandatory 
        DESCRIPTION   
                  " Current transaction level for this client. 0  indicates
          	    that the client is not currently involved in a transac-
          	    tion. "
        ::= { tuxTclientEntry 37 } 
  
tuxTclientId OBJECT-TYPE 
        SYNTAX  DisplayString (SIZE(1..78)) 
        ACCESS  read-only
        STATUS  mandatory 
        DESCRIPTION   
                  " Cient Identifier."
        ::= { tuxTclientEntry 38 } 

-- Added : BEGIN-JANUS-NS-TUXEDO7.1-041400

tuxTclientContextID OBJECT-TYPE 
        SYNTAX  INTEGER (-2..29999) 
        ACCESS  read-only
        STATUS  mandatory 
        DESCRIPTION   
	"Identifier for this particular application association. "
        ::= { tuxTclientEntry 50 } 
  
-- Added : END-JANUS-NS-TUXEDO7.1-041400

-- **************************************************************************
-- tuxTconn group
-- This represents runtime  attributes  of  active conversations within an 
-- application. 
-- **************************************************************************

tuxTconnTable	OBJECT-TYPE
	SYNTAX SEQUENCE OF TuxTconnEntry
	ACCESS not-accessible
	STATUS mandatory
	DESCRIPTION
		  " A list of active conversations in the application along
		    with their attributes. "
	::= { tuxTconn 1 }

tuxTconnEntry   OBJECT-TYPE 
        SYNTAX TuxTconnEntry 
        ACCESS not-accessible 
        STATUS mandatory 
        DESCRIPTION 
                  " A row in tuxTconnTable.

		NOTE:  All objects in this MIB group are local attributes i.e.
		       values for these objects correspond to the local host
		       only, where the TUXEDO agent is running. So the user needs
		       to run an instance of the TUXEDO agent on every node for
		       which these values are of interest."
	INDEX { tuxTconnSerNo }
        ::= { tuxTconnTable 1 } 
 
TuxTconnEntry ::= SEQUENCE {
	tuxTconnSerNo
		INTEGER,
	tuxTconnState
		INTEGER,
	tuxTconnSvcName
		DisplayString,
	tuxTconnClientId
		DisplayString,
	tuxTconnOgrpNo
		INTEGER,
	tuxTconnOlmid
		DisplayString,
	tuxTconnOpid
		INTEGER,
	tuxTconnOsndcnt
		INTEGER,
	tuxTconnOsrvId
		INTEGER,
	tuxTconnSgrpNo
		INTEGER,
	tuxTconnSlmid
		DisplayString,
	tuxTconnSpid
		INTEGER,
	tuxTconnSsndcnt
		INTEGER,
	tuxTconnSsrvId
		INTEGER
	}

tuxTconnSerNo   OBJECT-TYPE
        SYNTAX INTEGER
        ACCESS read-only
        STATUS mandatory
        DESCRIPTION       
		  " A running number as an index for tuxTconnTable. "
	::= { tuxTconnEntry 1 }
	
tuxTconnState   OBJECT-TYPE
        SYNTAX INTEGER {
		active(1)
	} 
        ACCESS read-only
        STATUS mandatory
        DESCRIPTION
                  " 
          GET:
               A GET operation will retrieve runtime  information
               for  the selected tuxTconnTable instance(s).  The following
               states indicate the meaning of a tuxTconnState returned
               in  response  to a GET request.  States not listed
               will not be returned.

               active(1)    The object returned reflects  one  or
                            both  sides of an active conversation
                            within the application."
        ::= { tuxTconnEntry 2 }
 
tuxTconnSvcName OBJECT-TYPE 
        SYNTAX DisplayString (SIZE(1..15)) 
        ACCESS read-only
        STATUS mandatory 
        DESCRIPTION    
                  " Service name of the conversational service  invoked  by
          	    the originator and processed by the subordinate. "
        ::= { tuxTconnEntry 3 }
 
tuxTconnClientId OBJECT-TYPE  
        SYNTAX DisplayString (SIZE(1..78)) 
        ACCESS read-only
        STATUS mandatory    
        DESCRIPTION     
                  " Client identifier.  The data in this field  should  not
          	    be  interpreted  directly  by  the  end user except for
          	    equality comparison. "
        ::= { tuxTconnEntry 4 } 

 tuxTconnOgrpNo OBJECT-TYPE  
        SYNTAX INTEGER (1..30001) 
        ACCESS read-only
        STATUS mandatory    
        DESCRIPTION     
                  " 
          	   Server group number for the originator of the conversa-
          	   tion.   If  the  originator is a client, then 30,000 is
          	   returned as the value for this attribute. "
        ::= { tuxTconnEntry 5 } 

 tuxTconnOlmid OBJECT-TYPE   
        SYNTAX DisplayString (SIZE(1..30))  
        ACCESS read-only
        STATUS mandatory     
        DESCRIPTION      
                  " Logical machine identifier indicating where the  origi-
          	    nator  is  running  or is accessing the application (in
          	    the case of /WS clients). "
        ::= { tuxTconnEntry 6 }  
  
 tuxTconnOpid OBJECT-TYPE   
        SYNTAX INTEGER 
        ACCESS read-only
        STATUS mandatory     
        DESCRIPTION      
                  " Process identifier for the originator of the  conversa-
          	    tion. "
        ::= { tuxTconnEntry 7 }  
  
 tuxTconnOsndcnt OBJECT-TYPE   
        SYNTAX INTEGER 
        ACCESS read-only
        STATUS mandatory     
        DESCRIPTION      
                  " Number of tpsend(3) calls done by the originator. "
        ::= { tuxTconnEntry 8 }  
  
 tuxTconnOsrvId OBJECT-TYPE   
        SYNTAX INTEGER (1..30001) 
        ACCESS read-only
        STATUS mandatory     
        DESCRIPTION      
                  " Server identifier for the originator of  the  conversa-
          	    tion. "
        ::= { tuxTconnEntry 9 }  
  
 tuxTconnSgrpNo OBJECT-TYPE   
        SYNTAX INTEGER (1..30001) 
        ACCESS read-only
        STATUS mandatory     
        DESCRIPTION      
                  " Server group number for the subordinate of the conversa-
          	    tion.   If  the  originator is a client, then 30,000 is
          	    returned as the value for this attribute."
        ::= { tuxTconnEntry 10 }  
  
 tuxTconnSlmid OBJECT-TYPE   
        SYNTAX DisplayString (SIZE(1..30))  
        ACCESS read-only
        STATUS mandatory     
        DESCRIPTION      
                  " Logical machine identifier indicating where the  subor-
          	    dinate  is  running or is accessing the application (in
          	    the case of /WS clients). "
        ::= { tuxTconnEntry 11 }  
  
 tuxTconnSpid OBJECT-TYPE   
        SYNTAX INTEGER 
        ACCESS read-only
        STATUS mandatory     
        DESCRIPTION      
                  " Process identifier for the subordinate in the conversa-
          	    tion. "
        ::= { tuxTconnEntry 12 }  
  
 tuxTconnSsndcnt OBJECT-TYPE   
        SYNTAX INTEGER 
        ACCESS read-only
        STATUS mandatory     
        DESCRIPTION      
                  " Number of tpsend(3) calls done by the subordinate. "
        ::= { tuxTconnEntry 13 }  
  
 tuxTconnSsrvId OBJECT-TYPE   
        SYNTAX INTEGER (1..30001) 
        ACCESS read-only
        STATUS mandatory     
        DESCRIPTION      
                  " Server identifier for the subordinate in the  conversa-
          	    tion. "
        ::= { tuxTconnEntry 14 }  


-- **************************************************************************  
-- tuxTwhichCfgDev control object
-- The value of this object determines the device for which tuxTdeviceTbl
-- returns configuration and runtime information.
-- **************************************************************************  
 tuxTwhichCfgDev OBJECT-TYPE
        SYNTAX DisplayString (SIZE(2..40))
        ACCESS read-write
        STATUS mandatory
        DESCRIPTION
                  " The value of this object determines the device for 
		    which tuxTdeviceTbl returns configuration and runtime
		    information. 
		    The default value of this object is the TUXCONFIG file
		    for the current domain."
        ::= { tuxTdevice 2 } 

-- **************************************************************************  
-- tuxTdevice group
-- This  represents  configuration  and  runtime
--   attributes  of  raw  disk  slices or UNIX System files being
--   used to store TUXEDO  System/T  device  lists.   This  class
--   allows  for the creation and deletion of device list entries
--   within a raw disk slice or UNIX System file.
-- **************************************************************************  

tuxTdeviceTbl   OBJECT-TYPE
        SYNTAX SEQUENCE OF TuxTdeviceEntry
        ACCESS not-accessible
        STATUS mandatory
        DESCRIPTION
                  "" 
        ::= { tuxTdevice 1 }

tuxTdeviceEntry   OBJECT-TYPE
        SYNTAX TuxTdeviceEntry
        ACCESS not-accessible
        STATUS mandatory
        DESCRIPTION
                  " A row in tuxTdeviceTbl.
  	 	    This group returns information about the Device as 
		    specified in tuxTwhichCfgDev.

		Row Creation
		============
		    To create a new row in this table, the user needs to send
		    a SET request, with atleast tuxTdevSize.

		NOTE:  All objects in this MIB group are local attributes i.e.
		====   values for these objects correspond to the local host
		       only, where the TUXEDO agent is running. So the user needs
		       to run an instance of the TUXEDO agent on every node for
		       which these values are of interest."
        INDEX { tuxTdevCfgDev, tuxTdevIndex }
        ::= { tuxTdeviceTbl 1 }

TuxTdeviceEntry ::= SEQUENCE {
        tuxTdevLmid
                DisplayString,
        tuxTdevCfgDev
                DisplayString,
        tuxTdeviceName
                DisplayString,
        tuxTdevOffset
                INTEGER,
        tuxTdevSize
                INTEGER,
        tuxTdevIndex
                INTEGER,
        tuxTdevState
                INTEGER
	}

 tuxTdevLmid OBJECT-TYPE
        SYNTAX DisplayString (SIZE(1..30))
        ACCESS read-write	-- writable only during row creation
        STATUS mandatory
        DESCRIPTION
                  " Logical machine identifier where the device is located.
          	    Note  that this attribute may be used as a key field in
          	    both unbooted and booted applications as long  as  they
          	    are already configured (that is, at least one tuxTmachine
          	    instance exits).  It is required as a  key  field  on
          	    SET operations when accessing a booted application.  If
          	    specified when  accessing  the  tuxTdevice  table  in  an
          	    unconfigured application, this attribute is ignored. 
		    Note: This object can be set only during row creation."
        ::= { tuxTdeviceEntry 1 }

 tuxTdevCfgDev OBJECT-TYPE 
        SYNTAX DisplayString (SIZE(2..40)) 
        ACCESS read-write	-- writable only during row creation
        STATUS mandatory 
        DESCRIPTION    
                  " Absolute pathname of the file or device where the  TUX-
          	    EDO System/T filesystem is stored or is to be stored. 
		    Note: This object can be set only during row creation."
        ::= { tuxTdeviceEntry 2 } 
 
 tuxTdeviceName OBJECT-TYPE 
        SYNTAX DisplayString (SIZE(2..256)) 
        ACCESS read-write	-- writable only during row creation
        STATUS mandatory 
        DESCRIPTION    
                  " Absolute pathname of the device list entry. 
		    Note: This object can be set only during row creation."
        ::= { tuxTdeviceEntry 3 } 
 
 tuxTdevOffset OBJECT-TYPE 
        SYNTAX INTEGER 
        ACCESS read-write	-- writable only during row creation
        STATUS mandatory 
        DESCRIPTION    
                  " The offset, in blocks, at which space on this tuxTdeviceName
          	    begins  for  use within the TUXEDO System/T VTOC speci-
          	    fied by tuxTdevCfgDev. 
		    Note: This object can be set only during row creation."
        ::= { tuxTdeviceEntry 4 } 
 
 tuxTdevSize OBJECT-TYPE 
        SYNTAX INTEGER 
        ACCESS read-write	-- writable only during row creation
        STATUS mandatory 
        DESCRIPTION    
                  " The size in pages of the disk area to be used  for  the
          	    device list entry.
		    Note: This object can be set only during row creation."
        ::= { tuxTdeviceEntry 5 } 
 
 tuxTdevIndex OBJECT-TYPE 
        SYNTAX INTEGER 
        ACCESS read-only
        STATUS mandatory 
        DESCRIPTION    
                  "  Device index  for  tuxTdevice  within  the  device  list
          	     addressed  by  tuxTdevCfgdev.   This  attribute value is
          	     used for identification purposes only  in  getting  and
          	     setting attribute values relating to particular devices
          	     within a TUXEDO System/T filesystem. "
        ::= { tuxTdeviceEntry 6 } 
 
 tuxTdevState OBJECT-TYPE 
        SYNTAX INTEGER {
		valid(1),
		invalid(2),
		re-init(3)
		} 
        ACCESS read-write
        STATUS mandatory 
        DESCRIPTION    
                  " 
          GET: 
               A GET operation will retrieve runtime  information
               for  the selected tuxTdeviceTbl instance(s).  The follow-
               ing states indicate  the  meaning  of  a  tuxTdevState
               returned in response to a GET request.  States not
               listed will not be returned.
               valid(1)     The TUXEDO System/T filesystem  indi-
                            cated by tuxTdevCfgDev exists and con-
                            tains a valid device list.  tuxTdevice
                            is   a   valid   device  within  that
                            filesystem  with  the  device   index
                            tuxTdevIndex.
          SET: 
               A SET operation will update  information  for  the
               selected  tuxTdeviceTbl instance or add the indicated
               object.  The following states indicate the meaning
               of  a  tuxTdevState set in a SET request.  States not
               listed may not be set.

               invalid(2)   Delete tuxTdeviceTbl instance for applica-
                            tion.  State change allowed only when
                            in  the  valid(1) state.    Successful
                            return   leaves  the  object  in  the
                            invalid(2) state.  Note that tuxTdevIndex
                            0  is  special  and  must  be deleted
                            last. 
		re-init(3)  To re-initialize a valid device. "
        ::= { tuxTdeviceEntry 7 } 

-- **************************************************************************
-- tuxTserver group
-- This group represents configuration  and  runtime attributes  of  servers 
-- within an application.  These attribute values identify and characterize 
-- configured servers  as well as provide runtime tracking of statistics and 
-- resources associated with each server object. 
-- **************************************************************************

tuxTsrvrTbl OBJECT-TYPE
	SYNTAX SEQUENCE OF TuxTsrvrEntry
	ACCESS	not-accessible
	STATUS	mandatory
	DESCRIPTION
		  ""
	::= { tuxTserver 1 }

tuxTsrvrEntry OBJECT-TYPE
	SYNTAX 	TuxTsrvrEntry
	ACCESS 	not-accessible
	STATUS	mandatory
	DESCRIPTION
		   " A row in tuxTsrvrTbl. To create a new row in
		     this table the following info. MUST be provided
		     in the set request - tuxTsrvrGrp & tuxTsrvrName. "
	INDEX { tuxTsrvrGrpNo,tuxTsrvrId }
	::=  { tuxTsrvrTbl 1 }

TuxTsrvrEntry ::= SEQUENCE {
	tuxTsrvrGrp
		DisplayString,
	tuxTsrvrId
		INTEGER,
	tuxTsrvrName
		DisplayString,
	tuxTsrvrGrpNo
		INTEGER,
	tuxTsrvrState
		INTEGER,
	tuxTsrvrBaseSrvId
		INTEGER,
	tuxTsrvrClOpt
		DisplayString,
	tuxTsrvrEnvFile
		DisplayString,
	tuxTsrvrGrace
		INTEGER,
	tuxTsrvrMaxgen
		INTEGER,
	tuxTsrvrMax
		INTEGER,
	tuxTsrvrMin
		INTEGER,
	tuxTsrvrRcmd
		DisplayString,
	tuxTsrvrRestart
		INTEGER,
	tuxTsrvrSequence
		INTEGER,
	tuxTsrvrSystemAccess
		INTEGER,
	tuxTsrvrConv
		INTEGER,
	tuxTsrvrReplyQ
		INTEGER,
	tuxTsrvrRpPerm
		DisplayString,
	tuxTsrvrRqAddr
		DisplayString,
	tuxTsrvrRqPerm
		DisplayString,
	tuxTsrvrGeneration
		INTEGER,
	tuxTsrvrPid
		INTEGER,
	tuxTsrvrRpid
		INTEGER,
	tuxTsrvrRqId
		INTEGER,
	tuxTsrvrTimeRestart
		INTEGER,
	tuxTsrvrTimeStart
		INTEGER,
	tuxTsrvrMinDispatchThreads
		INTEGER,
	tuxTsrvrMaxDispatchThreads
		INTEGER,
	tuxTsrvrThreadStackSize
		INTEGER
	}
	
tuxTsrvrGrp OBJECT-TYPE
        SYNTAX  DisplayString (SIZE(1..30))
        ACCESS  read-write	-- writable only during row creation
        STATUS  mandatory
        DESCRIPTION
                   " Logical name of the server group.  Server  group  names
          	     cannot contain an asterisk (*), comma, or colon. 
		    Note: This object can be set only during row creation."
        ::=  { tuxTsrvrEntry 1 }

tuxTsrvrId OBJECT-TYPE        
        SYNTAX  INTEGER (1..30001) 
        ACCESS  read-write	-- writable only during row creation
        STATUS  mandatory 
        DESCRIPTION 
                   " Unique (within the server group) server  identification
          	     number. 
		     Note: This object can be set only during row creation."
        ::=  { tuxTsrvrEntry 2 } 
 
tuxTsrvrName OBJECT-TYPE        
        SYNTAX  DisplayString (SIZE(1..256)) 
        ACCESS  read-write
        STATUS  mandatory 
        DESCRIPTION 
                   " Name of the server executable file.  The server identi-
          	     fied  by tuxTsrvrName will run on the machine(s) iden-
          	     tified  by  the tuxTgroup:tuxTgroupLmid object for this
          	     server's  server  group.   If  a  relative  pathname is
          	     given, then the search for the executable file is  done
          	     first in tuxTmachineAppDir, then in tuxTmachineTuxDir/bin, 
		     then in /bin and /usr/bin, and then in <path>, where 
		     <path>  is  the value  of the first PATH= line appearing 
	 	     in the machine environment file, if one exists.  Note that 
		     the  attribute value returned for an active server will 
		     always be a full pathname. "
        ::=  { tuxTsrvrEntry 3 } 
 
tuxTsrvrGrpNo OBJECT-TYPE         
        SYNTAX  INTEGER (1..30000) 
        ACCESS  read-only
        STATUS  mandatory  
        DESCRIPTION  
                   " Group number associated with this server's group. "
        ::=  { tuxTsrvrEntry 4 }  
  
tuxTsrvrState OBJECT-TYPE         
        SYNTAX  INTEGER {
		active(1),
		inactive(2),
		migrating(3),
		cleaning(4),
		restarting(5),
		suspended(6),
		partitioned(7),
		dead(8),
		invalid(10)
		} 
        ACCESS  read-write
        STATUS  mandatory  
        DESCRIPTION  
                   "  
	  GET: A  GET  operation  will retrieve configuration and
               runtime information  for  the  selected  tuxTserver
               instance(s). The  following  states  indicate  the
               meaning of a tuxTsrvrState returned in response to a
               GET  request.   States  not  listed  will  not  be
               returned.

               active(1)    tuxTserver instance defined  and  active.
                            This  is not an indication of whether
                            the  server  is  idle  or  busy.   An
                            active  server  with  a  non 0-length
                            tuxTsrvrCurSvc  attribute  should  be
                            interpreted  as  a  busy server, that
                            is, one that is processing a  service
                            request.

               inactive(2)  tuxTserver instance defined and inactive.

               migrating(3) tuxTserver instance defined and currently
                            in a state of migration to the server
                            group's  secondary  logical  machine.
                            The  secondary logical machine is the
                            one listed in tuxTgroupLmid  attribute   
			    that   does   not   match  the 
		            tuxTgroupCurLmid  object. 

               cleaning(4)  tuxTserver instance defined and currently
                            being  cleaned up after by the system
                            due to an abnormal death.  Note  that
                            restartable  servers  may  enter this
                            state  if   they   exceed   tuxTsrvrMaxgen
                            starts/restarts within their tuxTsrvrGrace
                            period.

               restarting(5)
			    tuxTserver instance defined and currently
                            being  restarted by the system due to
                            an abnormal  death. 

               suspended(6) tuxTserver instance defined and currently
                            suspended   pending  shutdown.

               partitioned(7)
			    tuxTserver instance defined  and  active;
                            however, the machine where the server
                            is running is  currently  partitioned
                            from   the  tuxTdomainMaster  site.

               dead(8)      tuxTserver instance  defined,  identified
                            as  active in the bulletin board, but
                            currently  not  running  due  to   an
                            abnormal   death. This state will
                            exist only until the BBL local to the
                            server  notices  the  death and takes
                            action  (REStarting|CLEaning).  
          SET: 
               A SET operation will update configuration and run-
               time information for the selected tuxTserver instance.
               The following states indicate  the  meaning  of  a
               tuxTsrvrState  set in a SET request.  States not listed
               may not be set.


               invalid(10)  Delete tuxTserver instance for applica-
                            tion.  State change allowed only when
                            in the  inactive(2)  state.  Successful
                            return   leaves  the  object  in  the
                            invalid(2) state.

               active(1)    Activate the tuxTserver instance. State
                            change allowed only when in the inac-
                            tive(2) state. (Servers in the migrating(3)
                            state  must  be  restarted by setting
                            the tuxTgroupState to active(1).).
                            Successful  return  leaves the object in
                            the active(1) state.

               inactive(2)  Deactivate the tuxTserver instance.
                            State change allowed only when in the
                            active(1) state. Successful   return
                            leaves  the  object  in  the inactive(2)
                            state.

               dead(8)      Deactivate the tuxTserver instance by
                            sending  the  server a SIGTERM signal
                            followed by a SIGKILL signal  if  the
                            server  is  still  running  after 20
                            seconds. Note that by default, a 
			    SIGTERM signal will cause the server to 
			    initiate orderly shutdown and the server  
			    will  become inactive  even  if it is 
			    restartable.
                            If a server is processing a long run-
                            ning service or has chosen to disable
                            the SIGTERM signal, then SIGKILL  may
                            be  used  and  will be treated by the
                            system as  an  abnormal  termination.
                            State change allowed only when in the
                            active(1) or suspended(6) state.   Success-
                            ful  return  leaves the object in the
                            inactive(2), cleaning(4) or restarting(5)
                            state. "
        ::=  { tuxTsrvrEntry 5 }  
  
tuxTsrvrBaseSrvId OBJECT-TYPE         
        SYNTAX  INTEGER (1..30001) 
        ACCESS  read-only
        STATUS  mandatory  
        DESCRIPTION  
                   " Base server identifier. For servers with a tuxTsrvrMax
          	     attribute value of 1, this attribute will always be the
          	     same as tuxTsrvrId.  However, for servers with  a  
		     tuxTsrvrMax value  of  greater than 1, this attribute 
		     indicates the base server identifier for the set of  
		     servers  configured identically. "
        ::=  { tuxTsrvrEntry 6 }  
  
tuxTsrvrClOpt OBJECT-TYPE         
        SYNTAX  DisplayString (SIZE(0..256))  
        ACCESS  read-write
        STATUS  mandatory  
        DESCRIPTION  
                   " Command line options to be passed to server when it  is
          	     activated.    See   the  servopts(5)  manual  page  for
          	     details.

          	     Limitation: Runtime  modifications  to  this  attribute
          	     will not affect a running server. "
        ::=  { tuxTsrvrEntry 7 }  
  
tuxTsrvrEnvFile OBJECT-TYPE         
        SYNTAX  DisplayString (SIZE(0..256))  
        ACCESS  read-write
        STATUS  mandatory  
        DESCRIPTION  
                   " Server     specific     environment     file.       See
          	     tuxTmachineEnvFile  for  a complete discussion of how
          	     this file is used to modify the environment.
          	     Limitation: Runtime  modifications  to  this  attribute
          	     will not affect a running server. "
        ::=  { tuxTsrvrEntry 8 }  
  
tuxTsrvrGrace OBJECT-TYPE         
        SYNTAX  INTEGER 
        ACCESS  read-write
        STATUS  mandatory  
        DESCRIPTION  
                   " The  period  of  time,  in  seconds,  over  which   the
          	     tuxTsrvrMaxgen  limit  applies.   This attribute is
          	     meaningful only for restartable servers,  that  is,  if
          	     the  tuxTsrvrRestart attribute is set to yes(1).  When
          	     a restarting server would exceed  the  tuxTsrvrMaxgen limit
          	     but  the tuxTsrvrGrace period has expired, the system 
		     resets the current generation  (tuxTsrvrGeneration)  to  1
          	     and      resets      the      initial     boot     time
          	     (tuxTsrvrTimeStart) to the current time.   A  value
          	     of  0 for this attribute indicates that a server should
          	     always be restarted.
	     
          	     Note that servers sharing a  request  queue  (that  is,
          	     equal  values for tuxTsrvrRqAddr) should have equal
          	     values for this attribute.  If they do  not,  then  the
          	     first server activated will establish the runtime value
          	     associated with all servers on the queue.
          	     Limitation: Runtime  modifications  to  this  attribute
          	     will  affect  a  running  server  and  all other active
          	     servers with which it is sharing a request queue.  How-
          	     ever,  only the selected server's configuration parame-
          	     ter is modified.  Thus, the behavior of the application
          	     depends  on the order of boot in subsequent activations
          	     unless the administrator ensures that all servers shar-
          	     ing a queue have the same value for this attribute. "
        ::=  { tuxTsrvrEntry 9 }  
  
tuxTsrvrMaxgen OBJECT-TYPE         
        SYNTAX  INTEGER (0..256) 
        ACCESS  read-write
        STATUS  mandatory  
        DESCRIPTION  
                   " Number of generations allowed for a restartable  server
          	     (tuxTsrvrRestart  ==  yes(1)) over the specified grace
          	     period (tuxTsrvrGrace).  The initial activation  of
          	     the  server  counts  as one generation and each restart
          	     also counts as one.  Processing after the maximum  gen-
          	     erations is exceeded is discussed above with respect to
          	     tuxTsrvrGrace.

          	     Note that servers sharing a  request  queue  (that  is,
          	     equal  values for tuxTsrvrRqAddr) should have equal
          	     values for this attribute.  If they do  not,  then  the
          	     first server activated will establish the runtime value
          	     associated with all servers on the queue.
          	     Limitation: Runtime  modifications  to  this  attribute
          	     will  affect  a  running  server  and  all other active
          	     servers with which it is sharing a request queue.  How-
          	     ever,  only the selected server's configuration parame-
          	     ter is modified.  Thus, the behavior of the application
          	     depends  on the order of boot in subsequent activations
          	     unless the administrator ensures that all servers shar-
          	     ing a queue have the same value for this attribute. "
        ::=  { tuxTsrvrEntry 10 }  
  
tuxTsrvrMax OBJECT-TYPE         
        SYNTAX  INTEGER (1..1001) 
        ACCESS  read-write
        STATUS  mandatory  
        DESCRIPTION  
                   " Maximum number of  occurrences  of  the  server  to  be
          	     booted.   Initially,  tmboot(1)  boots  tuxTsrvrMin
          	     objects of the server, and additional  objects  may  be
          	     started  individually  (by starting a particular server
          	     id)  or  through  automatic  spawning   (conversational
          	     servers only).  Runtime modifications to this attribute
          	     will affect all running servers in the set  of  identi-
          	     cally  configured  servers  (see tuxTsrvrBaseSrvId above) 
		     as well as the configuration definition of the server."
        ::=  { tuxTsrvrEntry 11 }  
  
tuxTsrvrMin OBJECT-TYPE         
        SYNTAX  INTEGER (1..1001)
        ACCESS  read-write
        STATUS  mandatory  
        DESCRIPTION  
                   " Minimum number of  occurrences  of  the  server  to  be
          	     booted by tmboot(1).  If a tuxTsrvrRqAddr is speci-
          	     fied and tuxTsrvrMin is greater than  1,  then  the  
		     servers will  form an MSSQ set.  The server identifiers 
		     for the servers will be  tuxTsrvrId  up  to  tuxTsrvrId +
          	     tuxTsrvrMax - 1.   All  occurrences of the server
          	     will have the same sequence  number,  as  well  as  any
          	     other server parameters.
	     
          	     Limitation: Runtime  modifications  to  this  attribute
          	     will not affect a running server. "
        ::=  { tuxTsrvrEntry 12 }  
  
tuxTsrvrRcmd OBJECT-TYPE         
        SYNTAX  DisplayString (SIZE(0..256))  
        ACCESS  read-write
        STATUS  mandatory  
        DESCRIPTION  
                   " Application specified command to be executed in  paral-
          	     lel  with  the system restart of an application server.
          	     This command must be an executable file.
          	     Note that servers sharing a  request  queue  (that  is,
          	     equal  values for tuxTsrvrRqAddr) should have equal
          	     values for this attribute.  If they do  not,  then  the
          	     first server activated will establish the runtime value
          	     associated with all servers on the queue.
	     
          	     Limitation: Runtime  modifications  to  this  attribute
          	     will  affect  a  running  server  and  all other active
          	     servers with which it is sharing a request queue.  How-
          	     ever,  only the selected server's configuration parame-
          	     ter is modified.  Thus, the behavior of the application
          	     depends  on the order of boot in subsequent activations
          	     unless the administrator ensures that all servers shar-
          	     ing a queue have the same value for this attribute. "
        ::=  { tuxTsrvrEntry 13 }  
  
tuxTsrvrRestart OBJECT-TYPE         
        SYNTAX  INTEGER {
		yes(1),
		no(2)
		} 
        ACCESS  read-write
        STATUS  mandatory  
        DESCRIPTION  
                   " Restartable yes(1) or non-restartable no(2) server.   If
          	     server  migration  is  specified  for this server group
          	     (tuxTdomainOptions = migrate(2) and  tuxTgroupLmid  with
          	     alternate  site),  then  this  attribute must be set to
          	     yes(1).
          	     Note that servers sharing a  request  queue  (that  is,
          	     equal  values for tuxTsrvrRqAddr) should have equal
          	     values for this attribute.  If they do  not,  then  the
          	     first server activated will establish the runtime value
          	     associated with all servers on the queue.
	     
          	     Limitation: Runtime  modifications  to  this  attribute
          	     will  affect  a  running  server  and  all other active
          	     servers with which it is sharing a request queue.  How-
          	     ever,  only the selected server's configuration parame-
          	     ter is modified.  Thus, the behavior of the application
          	     depends  on the order of boot in subsequent activations
          	     unless the administrator ensures that all servers shar-
          	     ing a queue have the same value for this attribute. "
        ::=  { tuxTsrvrEntry 14 }  
  
tuxTsrvrSequence OBJECT-TYPE
        SYNTAX  INTEGER (1..10000) 
        ACCESS  read-write
        STATUS  mandatory
        DESCRIPTION
                   " Specifies when this server should be booted (tmboot(1))
          	     or  shutdown (tmshutdown(1)) relative to other servers.
          	     If two servers are given the same sequence  number,  it
          	     is  possible for tmboot(1) to boot them in parallel and
          	     for  tmshutdown(1)  to  shut  them  down  in  parallel.
          	     tuxTsrvrEntry  instances added without a tuxTsrvrSequence 
		     attribute specified or with an invalid value will have  
		     one  generated  for  them  that is 10,000 or more and is 
		     higher than any other automatically  selected  default  
	 	     value.
          	     Servers  are booted by tmboot(1) in increasing order of
          	     sequence  number  and  shutdown  by  tmshutdown(1)   in
          	     decreasing order.  Runtime modifications to this attri-
          	     bute affect only tmboot(1) and tmshutdown(1)  and  will
          	     affect  the order in which running servers may be shut-
          	     down by a subsequent invocation of tmshutdown(1). "
        ::=  { tuxTsrvrEntry 15 }
 
tuxTsrvrSystemAccess OBJECT-TYPE
        SYNTAX  INTEGER {
		fastpath(1),
		protected(2)
		} 
        ACCESS  read-write
        STATUS  mandatory
        DESCRIPTION
                   " Mode used by System/T libraries within this server pro-
          cess to gain access to System/T's internal tables.  See
          tuxTdomainSystemAccess for a complete discussion  of
          this attribute.

          Limitation: Runtime  modifications  to  this  attribute
          will not affect a running server. "
        ::=  { tuxTsrvrEntry 16 }
 
tuxTsrvrConv OBJECT-TYPE
        SYNTAX  INTEGER {
		yes(1),
		no(2)
		} 
        ACCESS  read-write
        STATUS  mandatory
        DESCRIPTION
                   " Conversational server yes(1) or request/response  server
          	     no(2). "
        ::=  { tuxTsrvrEntry 17 }
 
tuxTsrvrReplyQ OBJECT-TYPE
        SYNTAX  INTEGER { 
                yes(1), 
                no(2) 
                } 
        ACCESS  read-write
        STATUS  mandatory
        DESCRIPTION
                   " Allocate  a  separate  reply  queue  for   the   server
          	     (tuxTsrvrReplyQ == yes(1)).   MSSQ  servers  that  expect  
		     to receive replies should set this attribute to yes(1). "
        ::=  { tuxTsrvrEntry 18 }
 
tuxTsrvrRpPerm OBJECT-TYPE
        SYNTAX  DisplayString (SIZE(4)) 
        ACCESS  read-write
        STATUS  mandatory
        DESCRIPTION
                   " UNIX System permissions for the server's  reply  queue.
          	     If a separate   reply   queue   is   not  allocated
          	     (tuxTsrvrReplyQ == no(2)),  then  this  attribute  is
          	     ignored.
		     Format: 0ddd, where d is a number 0 through 7. 
          	     Limitation: This is a UNIX  System  specific  attribute
          	     that  may  not be returned if the platform on which the
          	     application is being run is not UNIX-based. "
        ::=  { tuxTsrvrEntry 19 }
 
tuxTsrvrRqAddr OBJECT-TYPE
        SYNTAX  DisplayString (SIZE(0..30))
        ACCESS  read-write
        STATUS  mandatory
        DESCRIPTION
                   " Symbolic address of the request queue for  the  server.
          	     Specifying  the same tuxTsrvrRqAddr attribute value for 
		     more than one server is  the  way  multiple  server,  
		     single queue  (MSSQ)  sets are defined.  Servers with the 
		     same tuxTsrvrRqAddr attribute value must be in  the  same  
		     server group. "
        ::=  { tuxTsrvrEntry 20 }
 
tuxTsrvrRqPerm OBJECT-TYPE
        SYNTAX  DisplayString (SIZE(4))
        ACCESS  read-write
        STATUS  mandatory
        DESCRIPTION
                   " UNIX System permissions for the server's request queue.
		     Format: 0ddd, where d is a number 0 through 7. 
          	     Limitation: This is a UNIX  System  specific  attribute
          	     that  may  not be returned if the platform on which the
          	     application is being run is not UNIX-based. "
        ::=  { tuxTsrvrEntry 21 }

tuxTsrvrGeneration OBJECT-TYPE
        SYNTAX  INTEGER (1..32768)
        ACCESS  read-only
        STATUS  mandatory
        DESCRIPTION
                   " Generation of the server.  When a server  is  initially
                     booted   via   tmboot(1)   or   activated  through  the
                     SNMP Agent, its generation is set to 1.  Each  time  the
                     server dies abnormally and is restarted, its generation
                     is incremented.  Note that when  tuxTsrvrMaxGen  is
                     exceeded  and tuxTsrvrGrace has expired, the server
                     will be restarted with the generation reset to 1. "
        ::=  { tuxTsrvrEntry 22 }
 
tuxTsrvrPid OBJECT-TYPE
        SYNTAX  INTEGER
        ACCESS  read-only
        STATUS  mandatory
        DESCRIPTION
                   " UNIX System process identifier for  the  server.   Note
                     that  this  may not be a unique attribute since servers
                     may be  located  on  different  machines  allowing  for
                     duplication of process identifiers.
                     Limitation: This is a UNIX  System  specific  attribute
                     that  may  not be returned if the platform on which the
                     application is being run is not UNIX-based. "
        ::=  { tuxTsrvrEntry 23 }
 
tuxTsrvrRpid OBJECT-TYPE
        SYNTAX  INTEGER
        ACCESS  read-only
        STATUS  mandatory
        DESCRIPTION
                   " UNIX System message queue identifier for  the  server's
                     reply  queue.   If  a separate reply queue is not allo-
                     cated (tuxTsrvrReplyQ == no(2) ), then this  attribute
                     value will be the same as tuxTsrvrRqid.
                     Limitation: This is a UNIX  System  specific  attribute
                     that  may  not be returned if the platform on which the
                     application is being run is not UNIX-based. "
        ::=  { tuxTsrvrEntry 24 }

tuxTsrvrRqId OBJECT-TYPE
        SYNTAX  INTEGER
        ACCESS  read-only
        STATUS  mandatory
        DESCRIPTION
                   " UNIX System message queue identifier for  the  server's
                     request  queue.  If a separate reply queue is not allo-
                     cated ( tuxTsrvrReplyQ == no(2) ), then this  attribute
                     value will be the same as tuxTsrvrRpid.
                     Limitation: This is a UNIX  System  specific  attribute
                     that  may  not be returned if the platform on which the
                     application is being run is not UNIX-based. "
        ::=  { tuxTsrvrEntry 25 }

tuxTsrvrTimeRestart OBJECT-TYPE
        SYNTAX  INTEGER
        ACCESS  read-only
        STATUS  mandatory
        DESCRIPTION
                   " Time, in seconds, since 00:00:00 UTC, January 1,  1970,
                     as   returned   by   the   time(2)   system   call   on
                     local host, when the server was last  started  or
                     restarted. "
        ::=  { tuxTsrvrEntry 26 }

tuxTsrvrTimeStart OBJECT-TYPE
        SYNTAX  INTEGER
        ACCESS  read-only
        STATUS  mandatory
        DESCRIPTION
                   " Time, in seconds, since 00:00:00 UTC, January 1,  1970,
                     as   returned   by   the   time(2)   system   call   on
                     local host, when the server  was  first  started.
                     Restarts  of  the  server do not reset this value; how-
                     ever,   if tuxTsrvrMaxGen   is    exceeded    and
                     tuxTsrvrGrace  is  expired,  this attribute will be
                     reset to the time of the restart. "
        ::=  { tuxTsrvrEntry 27 }

-- Added : BEGIN-JANUS-NS-TUXEDO7.1-041400

tuxTsrvrMinDispatchThreads OBJECT-TYPE
        SYNTAX  INTEGER (1..999)
        ACCESS  read-write
        STATUS  mandatory
        DESCRIPTION
     	"specifies the number of server dispatch threads started on initial
     server boot. This parameter is effective only if the server has been
     built with the buildserver -t command.

     The separate dispatcher thread that is used when tuxTsrvrMaxDispatchThreads
     > 1 is not counted as part of the tuxTsrvrMinDispatchThreads value. It is
     required that tuxTsrvrMinDispatchThreads <= tuxTsrvrMaxDispatchThreads. The
     default for this parameter is 0.
                     Support : Tuxedo 7.1 and later"
        ::=  { tuxTsrvrEntry 40 }

tuxTsrvrMaxDispatchThreads OBJECT-TYPE
        SYNTAX  INTEGER (0..999)
        ACCESS  read-write
        STATUS  mandatory
        DESCRIPTION
	"specifies the maximum number of concurrently dispatched threads which
     each server process may spawn. This parameter is effective only if the
     server has been built with the buildserver -t command.
 
     If tuxTsrvrMaxDispatchThreads > 1, then a separate dispatcher thread is used
     and does not count against this limit. It is required that
     tuxTsrvrMinDispatchThreads <= tuxTsrvrMaxDispatchThreads. If this parameter is
     not specified, the default is 1.
                     Support : Tuxedo 7.1 and later"
        ::=  { tuxTsrvrEntry 50 }

tuxTsrvrThreadStackSize OBJECT-TYPE
        SYNTAX  INTEGER (0..2147483647)
        ACCESS  read-write
        STATUS  mandatory
        DESCRIPTION
	"If this parameter is not specified or if the value specified is 0, the
     operating system default is used. This option has an effect on the
     server only when a value greater than 1 is specified for
     tuxTsrvrMaxDispatchThreads.
                     Support : Tuxedo 7.1 and later"
        ::=  { tuxTsrvrEntry 60 }

-- Added : END-JANUS-NS-TUXEDO7.1-041400

-- *************************************************************************
-- tuxTsrvrTblExt group
-- An extension of the tuxTsrvrTbl.
-- *************************************************************************

tuxTsrvrTblExt OBJECT-TYPE
        SYNTAX SEQUENCE OF TuxTsrvrEntryExt
        ACCESS  not-accessible
        STATUS  mandatory
        DESCRIPTION
                  ""
        ::= { tuxTserver 2 }
 
tuxTsrvrEntryExt OBJECT-TYPE
        SYNTAX  TuxTsrvrEntryExt
        ACCESS  not-accessible
        STATUS  mandatory
        DESCRIPTION
                   " A row in tuxTsrvrTblExt .

		NOTE:  All objects in this MIB group are local attributes i.e.
		       values for these objects correspond to the local host
		       only, where the TUXEDO agent is running. So the user needs
		       to run an instance of the TUXEDO agent on every node for
		       which these values are of interest."
        INDEX { tuxTsrvrGrpNoExt,tuxTsrvrIdExt }
        ::=  { tuxTsrvrTblExt 1 }

TuxTsrvrEntryExt ::= SEQUENCE {
        tuxTsrvrIdExt
                INTEGER,
        tuxTsrvrGrpExt
                DisplayString,
        tuxTsrvrGrpNoExt
                INTEGER,
        tuxTsrvrStateExt
                INTEGER,
        tuxTsrvrNumConv
                INTEGER,
        tuxTsrvrNumDeque
		INTEGER,
	tuxTsrvrNumEnque
		INTEGER,
	tuxTsrvrNumPost
		INTEGER,
	tuxTsrvrNumReq
		INTEGER,
	tuxTsrvrNumSubscribe
		INTEGER,
	tuxTsrvrNumTran
		INTEGER,
	tuxTsrvrTranAbt
		INTEGER,
	tuxTsrvrTranCmt
		INTEGER,
	tuxTsrvrTotReqC
		INTEGER,
	tuxTsrvrTotWorkL
		INTEGER,
	tuxTsrvrCltLmid
		DisplayString,
	tuxTsrvrCltPid
		INTEGER,
	tuxTsrvrCltReply
		INTEGER,
	tuxTsrvrCmtRet
		INTEGER,
	tuxTsrvrCurConv
		INTEGER,
	tuxTsrvrCurReq
		INTEGER,
	tuxTsrvrCurService
		DisplayString,
	tuxTsrvrCurTime
		INTEGER,
	tuxTsrvrLastGrp
		INTEGER,
	tuxTsrvrSvcTimeOut
		INTEGER,
	tuxTsrvrTimeLeft
		INTEGER,
	tuxTsrvrTranLev
		INTEGER,
	tuxSrvrCurObjsExt
		INTEGER,
	tuxSrvrCurInterfaceExt
		DisplayString,
	tuxTsrvrCurDispatchThreads
		INTEGER,
	tuxTsrvrHwDispatchThreads
		INTEGER,
	tuxTsrvrNumDispatchThreads
		INTEGER
	}
	
 
tuxTsrvrIdExt OBJECT-TYPE
        SYNTAX  INTEGER (1..30001) 
        ACCESS  read-only      -- for row creation use tuxTsrvrTbl 
        STATUS  mandatory
        DESCRIPTION
                   " Unique (within the server group) server  identification
                     number. "
        ::=  { tuxTsrvrEntryExt 1 }
 
tuxTsrvrGrpNoExt OBJECT-TYPE
        SYNTAX  INTEGER (1..30000)
        ACCESS  read-only      --  for row creation use tuxTsrvrTbl
        STATUS  mandatory
        DESCRIPTION
                   " Group number associated with this server's group. "
        ::=  { tuxTsrvrEntryExt 2 }
 
tuxTsrvrNumConv OBJECT-TYPE
        SYNTAX  INTEGER
        ACCESS  read-only
        STATUS  mandatory
        DESCRIPTION
                   " Number of conversations initiated by  this  server  via
          	     tpconnect(3). "
        ::=  { tuxTsrvrEntryExt 3 }
 
tuxTsrvrNumDeque OBJECT-TYPE
        SYNTAX  INTEGER
        ACCESS  read-only
        STATUS  mandatory
        DESCRIPTION
                   " Number of dequeue operations initiated by  this  server
          	     via tpdequeue(3). "
        ::=  { tuxTsrvrEntryExt 4 }
 
tuxTsrvrNumEnque OBJECT-TYPE
        SYNTAX  INTEGER
        ACCESS  read-only
        STATUS  mandatory
        DESCRIPTION
                   " Number of enqueue operations initiated by  this  server
          	     via tpenqueue(3). "
        ::=  { tuxTsrvrEntryExt 5 }
 
tuxTsrvrNumPost OBJECT-TYPE
        SYNTAX  INTEGER
        ACCESS  read-only
        STATUS  mandatory
        DESCRIPTION
                   " Number  of  postings  initiated  by  this  server   via
          	     tppost(3). "
        ::=  { tuxTsrvrEntryExt 6 }
 
tuxTsrvrNumReq OBJECT-TYPE
        SYNTAX  INTEGER
        ACCESS  read-only
        STATUS  mandatory
        DESCRIPTION
                   " Number of requests made by this server via tpcall(3) or
          	     tpacall(3). "
        ::=  { tuxTsrvrEntryExt 7 }
 
tuxTsrvrNumSubscribe OBJECT-TYPE
        SYNTAX  INTEGER
        ACCESS  read-only
        STATUS  mandatory
        DESCRIPTION
                   " Number of subscriptions made by this server via  tpsub-
          	     scribe(3). "
        ::=  { tuxTsrvrEntryExt 8 }
 
tuxTsrvrNumTran OBJECT-TYPE
        SYNTAX  INTEGER
        ACCESS  read-only
        STATUS  mandatory
        DESCRIPTION
                   " Number of transactions begun by this server  since  its
          	     last (re)start. "
        ::=  { tuxTsrvrEntryExt 9 }
 
tuxTsrvrTranAbt OBJECT-TYPE
        SYNTAX  INTEGER
        ACCESS  read-only
        STATUS  mandatory
        DESCRIPTION
                   " Number of transactions aborted by this server since its
          	     last (re)start. "
        ::=  { tuxTsrvrEntryExt 10 }
 
tuxTsrvrTranCmt OBJECT-TYPE
        SYNTAX  INTEGER
        ACCESS  read-only
        STATUS  mandatory
        DESCRIPTION
                   " Number of transactions committed by this  server  since
          	     its last (re)start. "
        ::=  { tuxTsrvrEntryExt 11 }
 
tuxTsrvrTotReqC OBJECT-TYPE
        SYNTAX  INTEGER   
        ACCESS  read-only
        STATUS  mandatory
        DESCRIPTION
                   " Total number of requests completed by this server.  For
          	     conversational  servers (tuxTsrvrConv == yes(1))  this
          	     attribute  value  indicates  the  number  of  completed
          	     incoming  conversations.   This  is a runtime attribute
          	     that is kept across  server  restart  but  is  lost  at
          	     server shutdown. "
        ::=  { tuxTsrvrEntryExt 12 }
 
tuxTsrvrTotWorkL OBJECT-TYPE
        SYNTAX  INTEGER   
        ACCESS  read-only
        STATUS  mandatory
        DESCRIPTION
                   " Total workload completed by this server.  For conversa-
          	     tional  servers  (tuxTsrvrConv == yes(1)), this attri-
          	     bute value indicates the workload of completed incoming
          	     conversations.   This  is  a  runtime attribute that is
          	     kept across server restart but is lost at server  shut-
          	     down. "
        ::=  { tuxTsrvrEntryExt 13 }
 
tuxTsrvrCltLmid OBJECT-TYPE
        SYNTAX  DisplayString (SIZE(1..30))   
        ACCESS  read-only
        STATUS  mandatory
        DESCRIPTION
                   " Logical machine for the initiating  client  or  server.
          	     The  initiating  client  or  server is the process that
          	     made the service request that the server  is  currently
          	     working on. "
        ::=  { tuxTsrvrEntryExt 14 }
 
tuxTsrvrCltPid OBJECT-TYPE
        SYNTAX  INTEGER   
        ACCESS  read-only
        STATUS  mandatory
        DESCRIPTION
                   "  UNIX  System  process  identifier  for  the  initiating
          	      client or server. `
          	      Limitation: This is a UNIX  System  specific  attribute
          	      that  may  not be returned if the platform on which the
          	      application is being run is not UNIX-based. "
        ::=  { tuxTsrvrEntryExt 15 }
 
tuxTsrvrCltReply OBJECT-TYPE
        SYNTAX  INTEGER {
		yes(1),
		no(2),
		null(3)
		}  
        ACCESS  read-only
        STATUS  mandatory
        DESCRIPTION
                   " The initiating client or server is  expecting  a  reply
          	     yes(1) or is not expecting a reply no(2). "
        ::=  { tuxTsrvrEntryExt 16 }

tuxTsrvrCmtRet OBJECT-TYPE
        SYNTAX  INTEGER {
		complete(1),
		logged(2)
		} 
        ACCESS  read-only
        STATUS  mandatory
        DESCRIPTION
                   " Setting of  the  TP_COMMIT_CONTROL  characteristic  for
          	     this  server.  See the description of the System/T ATMI
          	     function tpscmt(3) for details on this characteristic. "
        ::=  { tuxTsrvrEntryExt 17 }
 
tuxTsrvrCurConv OBJECT-TYPE
        SYNTAX  INTEGER 
        ACCESS  read-only
        STATUS  mandatory
        DESCRIPTION
                   " Number of conversations initiated by  this  server  via
          	     tpconnect(3) that are still active. "
        ::=  { tuxTsrvrEntryExt 18 }
 
tuxTsrvrCurReq OBJECT-TYPE
        SYNTAX  INTEGER 
        ACCESS  read-only
        STATUS  mandatory
        DESCRIPTION
                   " Number  of  requests  initiated  by  this  server   via
          	     tpcall(3) or tpacall(3) that are still active. "
        ::=  { tuxTsrvrEntryExt 19 }
 
tuxTsrvrCurService OBJECT-TYPE
        SYNTAX  DisplayString (SIZE(1..15))
        ACCESS  read-only
        STATUS  mandatory
        DESCRIPTION
                   " Service name that the server is currently  working  on,
          	     if any. "
        ::=  { tuxTsrvrEntryExt 20 }
 
tuxTsrvrCurTime OBJECT-TYPE
        SYNTAX  INTEGER 
        ACCESS  read-only
        STATUS  mandatory
        DESCRIPTION
                   " Current time, in centi-seconds, since 00:00:00  UTC,  
		     January 1,  1970,  as on tuxTsrvrLmid. This attribute 
		     can be used  to  compute  elapsed  time  from the 
		     tuxTsrvrTimeStart and tuxTsrvrTimeRestart object values."
        ::=  { tuxTsrvrEntryExt 21 }
 
tuxTsrvrLastGrp OBJECT-TYPE
        SYNTAX  INTEGER (1..30000) 
        ACCESS  read-only
        STATUS  mandatory
        DESCRIPTION
                   "  Server group number (tuxTgroupNo) of the last ser-
          	      vice  request  made or conversation initiated from this
		      server outward. "
        ::=  { tuxTsrvrEntryExt 22 }
 
tuxTsrvrSvcTimeOut OBJECT-TYPE
        SYNTAX  INTEGER 
        ACCESS  read-only
        STATUS  mandatory
        DESCRIPTION
                   " Time left, in seconds, for this server to  process  the
          	     current  service  request, if any.  A value of 0 for an
          	     active service indicates that no timeout processing  is
          	     being   done.   See  tuxTsvcTimeOut  for  more
          	     information. "
        ::=  { tuxTsrvrEntryExt 23 }
 
tuxTsrvrTimeLeft OBJECT-TYPE
        SYNTAX  INTEGER 
        ACCESS  read-only
        STATUS  mandatory
        DESCRIPTION
                   " Time left, in seconds, for this server to  receive  the
          	     reply  for which it is currently waiting before it will
          	     timeout.  This timeout may be a  transactional  timeout
          	     or a blocking timeout. "
        ::=  { tuxTsrvrEntryExt 24 }
 
tuxTsrvrTranLev OBJECT-TYPE
        SYNTAX  INTEGER 
        ACCESS  read-only
        STATUS  mandatory
        DESCRIPTION
                   " Current transaction level for this server. 0  indicates
          	     that the server is not currently involved in a transac-
          	     tion. "
        ::=  { tuxTsrvrEntryExt 25 }

tuxTsrvrStateExt OBJECT-TYPE
        SYNTAX  INTEGER {
		active(1),
		inactive(2),
 	 	migrating(3),
                cleaning(4),
                restarting(5),
                suspended(6),
                partitioned(7),
                dead(8)
	}
        ACCESS  read-only
        STATUS  mandatory
        DESCRIPTION  
                   " Refer to description of tuxTsrvrState for details. " 
        ::=  { tuxTsrvrEntryExt 26 }

tuxTsrvrGrpExt OBJECT-TYPE
        SYNTAX  DisplayString
        ACCESS  read-only
        STATUS  mandatory
        DESCRIPTION  
                   " Name of group to which this server belongs. This object
		     is included for readability purposes only. " 
        ::=  { tuxTsrvrEntryExt 27 }

tuxSrvrCurObjsExt OBJECT-TYPE
        SYNTAX  INTEGER
        ACCESS  read-only
        STATUS  mandatory
        DESCRIPTION
                   " The number of entries in use in the bulletin board
                     object table for this server. "
        ::=  { tuxTsrvrEntryExt 32 }
 
tuxSrvrCurInterfaceExt OBJECT-TYPE
        SYNTAX  DisplayString (SIZE(0..128))
        ACCESS  read-only
        STATUS  mandatory
        DESCRIPTION
                   " The interface name of the interface currently active in
                     this server. "
        ::=  { tuxTsrvrEntryExt 37 }

-- Added : START-JANUS-NS-TUX7.1-041400

tuxTsrvrCurDispatchThreads OBJECT-TYPE
        SYNTAX  INTEGER
        ACCESS  read-only
        STATUS  mandatory
        DESCRIPTION
	"Current number of active service dispatch threads for this server. 
                     Support : Tuxedo 7.1 and later"
        ::=  { tuxTsrvrEntryExt 100 }

tuxTsrvrHwDispatchThreads OBJECT-TYPE
        SYNTAX  INTEGER
        ACCESS  read-only
        STATUS  mandatory
        DESCRIPTION
	 "Highest number of active service dispatch threads created for this
     server since its last restart. This number may differ from the number
     of service calls, since an administrator may specify parameters that
     control the caching of idle service threads.	
                     Support : Tuxedo 7.1 and later"
        ::=  { tuxTsrvrEntryExt 110 }

tuxTsrvrNumDispatchThreads OBJECT-TYPE
        SYNTAX  INTEGER
        ACCESS  read-only
        STATUS  mandatory
        DESCRIPTION
	"Total number of active service dispatch threads for this server since
     its last restart.
                     Support : Tuxedo 7.1 and later"
        ::=  { tuxTsrvrEntryExt 120 }

-- Added : END-JANUS-NS-TUX7.1-041400

-- *************************************************************************** 
-- tuxTsvcTbl 
-- This represents configuration  attributes  of
-- services  within  an  application.   These  attribute values
-- identify and characterize configured services.  A  tuxTsvc
-- object provides activation time configuration attributes for
-- services not specifically configured as part of the tuxTsvcGrp
-- group.
-- *************************************************************************** 

tuxTsvcTbl OBJECT-TYPE
        SYNTAX SEQUENCE OF TuxTsvcEntry
        ACCESS  not-accessible
        STATUS  mandatory
        DESCRIPTION
                  "Configuration attributes of services within an application."
        ::= { tuxTsvc 1 }

tuxTsvcEntry OBJECT-TYPE
        SYNTAX  TuxTsvcEntry
        ACCESS  not-accessible
        STATUS  mandatory
        DESCRIPTION
                   " A row in tuxTsvcTbl . 
		     Creation of a New row (instance ):
		     =================================
		     A SET request for any one or more valid non-existant object 
		     instances in the table will create an appropriate new row in 
		     the table. "
        INDEX { tuxTsvcName }
        ::=  { tuxTsvcTbl 1 }

TuxTsvcEntry ::= SEQUENCE {
        tuxTsvcName
                DisplayString,
        tuxTsvcType
                INTEGER,
        tuxTsvcState
                INTEGER,
        tuxTsvcAutoTran
                INTEGER,
        tuxTsvcLoad
                INTEGER,
        tuxTsvcPrio
                INTEGER,
        tuxTsvcTimeOut
                INTEGER,
        tuxTsvcTranTime
                INTEGER,
	tuxTsvcBufType
		DisplayString,
	tuxTsvcRoutingName
		DisplayString,
        tuxTsvcEncryptionRequired
                INTEGER,
        tuxTsvcSignatureRequired
                INTEGER
	}

tuxTsvcName OBJECT-TYPE 
        SYNTAX  DisplayString (SIZE(1..15))
        ACCESS  read-write	-- writable only during row creation
        STATUS  mandatory  
        DESCRIPTION 
                   " Service name. 
		     Note: This object can be set only during row creation."
        ::=  { tuxTsvcEntry 1 } 

tuxTsvcType OBJECT-TYPE
        SYNTAX  INTEGER {
		app(1),
		callable(2),
		system(3),
		unknown(4)
	}
        ACCESS  read-only
        STATUS  mandatory
        DESCRIPTION
                   " Type of service.  app(1) indicates an application defined 
 	   	     service name.  callable(2) indicates a system provided 
		     callable service.  system(3) indicates a system provided 
		     and system callable service.
           	     System services are not available to application clients 
		     and servers for direct access. "
        ::=  { tuxTsvcEntry 2 }
 
tuxTsvcState OBJECT-TYPE 
        SYNTAX  INTEGER {
		active(1),
		inactive(2),
		invalid(3)
		} 
        ACCESS  read-write
        STATUS  mandatory   
        DESCRIPTION  
                   " 
          GET:
               A GET operation will retrieve configuration infor-
               mation  for the selected tuxTsvc instance(s).  The
               following  states  indicate  the  meaning   of   a
               tuxTsvcState  returned  in  response to a GET request.
               States not listed will not be returned.

               active(1)    tuxTsvc instance is  defined  and  at
                            least  one  tuxTsvcGrp  object  with  a
                            matching  tuxTsvcName   value   is
                            active.

               inactive(2)  tuxTsvc instance is  defined  and  no
                            tuxTsvcGrp   object   with  a  matching
                            tuxTsvcName value is active.

          SET: 
               A SET operation will update configuration informa-
               tion  for the selected tuxTsvc instance.  The fol-
               lowing states indicate the meaning of  a  tuxTsvcState
               set  in  a SET request.  States not listed may not
               be set.


               invalid(3)   Delete tuxTsvc instance for  applica-
                            tion.  State change allowed only when
                            in the  inactive(2) state.   Successful
                            return   leaves  the  object  in  the
                            invalid(3) state. "
        ::=  { tuxTsvcEntry 3 }    
  
tuxTsvcAutoTran OBJECT-TYPE 
        SYNTAX  INTEGER {
		yes(1),
		no(2)
		} 
        ACCESS  read-write
        STATUS  mandatory   
        DESCRIPTION  
                   " Automatically begin a transaction (yes(1)) when a  service
          	     request  message  is  received  for this service if the
          	     request is not already in transaction mode.
          	     Limitation: Runtime updates to this attribute  are  not
          	     reflected in active tuxTsvcGrp objects. "
        ::=  { tuxTsvcEntry 4 }    
  
tuxTsvcLoad OBJECT-TYPE 
        SYNTAX  INTEGER (1..32767) 
        ACCESS  read-write
        STATUS  mandatory   
        DESCRIPTION  
                   " This tuxTsvc object imposes the indicated load on the
          	     system.  Service loads are used for load balancing pur-
          	     poses, that is, queues with higher  enqueued  workloads
          	     are  less  likely to be chosen for a new request.  Ser-
          	     vice loads have meaning only if  the  tuxTdomainLoadBalance
          	     is set to yes(1).
	     
          	     Limitation: Runtime updates to this attribute  are  not
          	     reflected in active tuxTsvcGrp objects. "
        ::=  { tuxTsvcEntry 5 }    
  
tuxTsvcPrio OBJECT-TYPE 
        SYNTAX  INTEGER (1..100) 
        ACCESS  read-write
        STATUS  mandatory   
        DESCRIPTION  
                   " This  tuxTsvc  object  has  the  indicated  dequeuing
          	     priority.   If multiple service requests are waiting on
          	     a queue for servicing,  the  higher  priority  requests
          	     will be serviced first.
          	     Limitation: Runtime updates to this attribute  are  not
          	     reflected in active tuxTsvcGrp objects. "
        ::=  { tuxTsvcEntry 6 }    
  
tuxTsvcTimeOut OBJECT-TYPE 
        SYNTAX  INTEGER 
        ACCESS  read-write
        STATUS  mandatory   
        DESCRIPTION  
                   " Time limit (in seconds)  for  processing  requests  for
          	    this service name.  Servers processing service requests
          	    for this service will be  abortively  terminated  (kill
          	    -9) if they exceed the specified time limit in process-
          	    ing the request.  A value of 0 for this attribute indi-
          	    cates   that  the  service  should  not  be  abortively
          	    terminated.
	    
          	    Limitation: Runtime updates to this attribute  are  not
          	    reflected in active tuxTsvcGrp objects.
          	    Limitation: This attribute value  is  not  enforced  on
          	    TUXEDO System/T Release 4.2.2 sites or earlier."
        ::=  { tuxTsvcEntry 7 }    
  
tuxTsvcTranTime OBJECT-TYPE 
        SYNTAX  INTEGER 
        ACCESS  read-write
        STATUS  mandatory   
        DESCRIPTION  
                   " Transaction timeout value in seconds  for  transactions
          	     automatically started for this tuxTsvc object.  Tran-
          	     sactions are started automatically when a  request  not
          	     in    transaction    mode    is    received   and   the
          	     tuxTsvcAutoTran attribute value for  the  service
          	     is yes(1).

          	     Limitation: Runtime updates to this attribute  are  not
          	     reflected in active tuxTsvcGrp objects. "
        ::=  { tuxTsvcEntry 8 }    
  
tuxTsvcBufType OBJECT-TYPE 
        SYNTAX  DisplayString (SIZE(1..256)) 
        ACCESS  read-write
        STATUS  mandatory   
        DESCRIPTION  
                   " type1[:subtype1[,subtype2 . . . ]][;type2[:subtype3[,...
		     ]]]...
          	     List  of types and subtypes of data buffers accepted by
          	     this service.  A maximum of  32  type/subtype  combina-
          	     tions are allowed.  Types of data buffers provided with
          	     TUXEDO  System/T  are  FML  (for  FML  buffers),  VIEW,
          	     X_C_TYPE,  or X_COMMON (for FMLviews), STRING (for NULL
          	     terminated character arrays),  and  CARRAY  or  X_OCTET
          	     (for  a  character  array  that  is neither encoded nor
          	     decoded during transmission).   Of  these  types,  only
          	     VIEW,  X_C_TYPE,  and  X_COMMON  have subtypes.  A VIEW
          	     subtype gives the name of the particular VIEW  expected
          	     by  the  service.   Application  types and subtypes can
          	     also be added (see tuxtypes(5)).   For  a  buffer  type
          	     that  has subtypes, ``*'' can be specified for the sub-
          	     type to indicate that the service accepts all  subtypes
          	     for the associated buffer type.
          	     A single service can only interpret a fixed  number  of
          	     buffer  types,  namely  those  found in its buffer type
          	     switch (see tuxtypes(5)).  If the tuxTsvcBufType  
          	     value  is  set  to  ALL,  that  service will accept all
          	     buffer types found in its buffer type switch.
	     
          	     A type name can be 8 characters or less in length and a
          	     subtype  name  can  be 16 characters or less in length.
          	     Note that type and subtype  names  should  not  contain
          	     semicolon, colon, comma, or asterisk characters.
          	     Limitation: This attribute value represents the  buffer
          	     types that must be supported by each and every instance
          	     of an  application  service  with  this  service  name.
          	     Since  this  attribute  value  is  processed at service
          	     activation time, updates to this attribute are  allowed
          	     only  when  there  are  no active tuxTsvcGrp objects with
          	     matching service names. "
        ::=  { tuxTsvcEntry 9 }    
  
tuxTsvcRoutingName OBJECT-TYPE
        SYNTAX  DisplayString (SIZE(0..15))
        ACCESS  read-write
        STATUS  mandatory
        DESCRIPTION
                   " This tuxTsvc object has the  indicated  routing  cri-
          	     teria  name.   Active updates to this attribute will be
          	     reflected in all associated tuxTsvcGrp objects. "
        ::=  { tuxTsvcEntry 10 }

-- Added : BEGIN-JANUS-NS-TUXEDO7.1-041400

tuxTsvcEncryptionRequired OBJECT-TYPE
        SYNTAX  INTEGER {
		yes(1),
		no(2)
	}
        ACCESS  read-write
        STATUS  mandatory
        DESCRIPTION
	"If set to yes every application service in this group requires an
     encrypted input message buffer. 
          	     Support: Tuxedo 7.1 and later. "
        ::=  { tuxTsvcEntry 20 }

tuxTsvcSignatureRequired OBJECT-TYPE
        SYNTAX  INTEGER {
		yes(1),
		no(2)
	}
        ACCESS  read-write
        STATUS  mandatory
        DESCRIPTION
	"If set to yes every application service in this group requires a valid
     digital signature on its input message buffer. 
	Support: Tuxedo 7.1 and later. "
        ::=  { tuxTsvcEntry 30 }

-- Added : END-JANUS-NS-TUXEDO7.1-041400
 
-- **************************************************************************
--  The tuxTsvcGrp group represents configuration and runtime
--  attributes of services/groups within an application.  These
--  attribute values identify and characterize configured
--  services/groups as well as provide runtime tracking of
--  statistics and resources associated with each object.
-- **************************************************************************

tuxTsvcGrp OBJECT-TYPE
        SYNTAX SEQUENCE OF TuxTsvcGrpEntry
        ACCESS  not-accessible
        STATUS  mandatory
        DESCRIPTION
                  "    
		   The tuxTsvcGrp group represents configuration and runtime 
		   attributes of services/groups within an application.  These 
		   attribute values identify and characterize configured 
		   services/groups as well as provide runtime tracking of 
		   statistics and resources associated with each object. 
     		   Both the tuxTsvcTbl  and  tuxTsvcGrp  define activation  time 
     		   attribute settings for service names within the application.  
     		   When a new service  is  activated  (advertised),  either due 
     		   to initial activation of a server or due
     		   to a call to tpadvertise(3), the following hierarchy  exists
     		   for  determining  the attribute values to be used at service
     		   startup time.
		   
     		   1.  If a matching configured tuxTsvcGrp object exists  (matching  
		       service name and server group), then the attributes defined 
		       in that object are used to  initially  configure the advert-
		       ised service.
		   
     		   2.  Otherwise, if a  matching  configured  tuxTsvcTbl  object
         	       exists  (matching  service  name),  then  the attributes
         	       defined in that object are used to  initially  configure
         	       the advertised service.
		   
     		   3.  Otherwise, if any configured tuxTsvcGrp objects are  found
         	       with  matching service name , then the first one found  is  
	 	       used  to  initially  configure  the advertised service.
		   
     		   4.  If none of the preceding cases is used, then the  system
         	       defaults  for  service  attributes are used to initially
         	       configure the advertised service. "
        ::= { tuxTsvc 2 }
 
tuxTsvcGrpEntry OBJECT-TYPE
        SYNTAX  TuxTsvcGrpEntry
        ACCESS  not-accessible
        STATUS  mandatory
        DESCRIPTION
                   " A row in tuxTsvcGrp.
		     Creation of New Row:
		     ====================
		     To create a new instance a SET request for atleast tuxTsvcGrpName is
		     required. 
		     The tuxTsvcGrpName/tuxTsvcGrpSvcName (in the index) combination 
		     should be a non-existant one. For activating instance(s) of existing 
		     tuxTsvcGrp entries refer to description of tuxTsvcSrvrId.

		     During creation, if tuxTsvcSrvrId (part of index) is zero the 
		     service entry is configured and not activated(advertised), else the 
		     service is activated also using the value of tuxTsvcSrvrId to 
		     identify the server instance. 

                NOTE:  All objects in this MIB group are local attributes i.e.
                       values for these objects correspond to the local host
                       only, where the TUXEDO agent is running. So the user needs
                       to run an instance of the TUXEDO agent on every node for
                       which these values are of interest."
        INDEX { tuxTsvcGrpSvcName, tuxTsvcGrpNo, tuxTsvcSrvrId }
        ::=  { tuxTsvcGrp 1 }

TuxTsvcGrpEntry ::= SEQUENCE {
        tuxTsvcGrpSvcName
                DisplayString,
        tuxTsvcGrpName
                DisplayString,
	tuxTsvcGrpNo
		INTEGER,
	tuxTsvcGrpState
		INTEGER,
	tuxTsvcGrpAutoTran
		INTEGER,
	tuxTsvcGrpLoad
		INTEGER,
	tuxTsvcGrpPrio
		INTEGER,
	tuxTsvcGrpSvcTimeOut
		INTEGER,
	tuxTsvcGrpTranTime
		INTEGER,
        tuxTsvcSrvrLmid
                DisplayString,
        tuxTsvcSrvrRqAddr
                DisplayString,
        tuxTsvcSrvrId
                INTEGER,
        tuxTsvcrName
                DisplayString,
        tuxTsvcSrvrNcompleted
                INTEGER,
        tuxTsvcSrvrNqueued
                INTEGER         
        }

tuxTsvcGrpSvcName OBJECT-TYPE
        SYNTAX  DisplayString (SIZE(1..15))
        ACCESS  read-write               
        STATUS  mandatory
        DESCRIPTION
                   " Service Name. 
		     Note: This object can be SET only during row creation."
        ::=  { tuxTsvcGrpEntry 1 }

tuxTsvcGrpName OBJECT-TYPE
        SYNTAX  DisplayString (SIZE(1..30))
        ACCESS  read-write
        STATUS  mandatory
        DESCRIPTION
                   " Server group name.  Server group names cannot contain 
		     an asterisk. 
		     Note: This object can be SET only during row creation."
        ::=  { tuxTsvcGrpEntry 2 } 
 
tuxTsvcGrpNo OBJECT-TYPE
        SYNTAX  INTEGER (1..29999)
        ACCESS  read-write
        STATUS  mandatory
        DESCRIPTION
                   " Server group number. 
		     Note: This object can be updated only during row creation."
        ::=  { tuxTsvcGrpEntry 3 } 

tuxTsvcGrpState OBJECT-TYPE
        SYNTAX  INTEGER {
		active(1),
		inactive(2),
		suspended(3),
		partitioned(4),
		invalid(5)
	} 
        ACCESS  read-write
        STATUS  mandatory
        DESCRIPTION
                   " GET
     active(1):      Atleast one instance is active, suspended or partitioned .

     inactive(2):    tuxTsvcGrp instance defined and inactive.

     suspended(3):   tuxTsvcGrp object defined, active,  and currently suspended.  This 
		     service is not available for access by the application in this state.  

     partitioned(4)  tuxTsvcGrp object defined, active,  and currently partitioned from the
		     master site of the application.  This  service  is  not available for 
		     access by the application in this state.

		     SET 

                     A SET operation will update configuration and run time information for 
		     the selected tuxTsvcGrp instance.  Note  that  runtime  modifications 
		     to a service object  may  affect  more  than one active server.  The 
		     following states indicate  the  meaning  of  a tuxTsvcGrpState set 
		     in a SET request. States not listed may not be set.  

     invalid(5):     it removes the corresponding tuxTsvcGrp instance. When a tuxTsvcGrp 
		     instance is deleted - it will also remove the associated tuxTsvcSrvr 
		     instances which correspond to server instances which are a part of 
		     this group advertising this service. This transition is permissible 
		     only in inactive(2) state.

     active(1)       Activate (advertise) the tuxTsvcGrp instance. 
		     State  change  allowed only when in the suspended(3) or invalid(5)  
		     states. Either tuxTsvcSrvrId or tuxTsvcSrvrRqAddr must be specified 
		     with this state  change. Successful return leaves the object in the 
		     active(1) state.

		     NOTE: To activate an object in the inactive(2) state, the user should
			   set tuxTsvcSrvrId(whose current value will be 0) to the server 
			   id of the corresponding server instance, where the service
			   is to be activated(advertised).

                     Limitation:  State change not permitted for service names beginning 
				  with  the reserved string `.'

      inactive(2)    Deactivate the tuxTsvcGrp instance. State change allowed only when in 
		     the suspended(3) state. Successful return leaves the object in either 
		     the inactive(2) (configured entries) or invalid(5) (unconfigured 
		     entries) state.

                     Limitation:  State change not permitted for service names beginning  
				  with the reserved string '_'. 

      suspended(3)   Suspend the tuxTsvcGrp object. State change allowed only when in the
                     active(1)  state. Successful return leaves the object in the 
		     suspended(3) state.

                     Limitation:  State change not permitted for service names beginning 
				  with  the reserved string '_'."
        ::=  { tuxTsvcGrpEntry 4 }
 
 
tuxTsvcGrpAutoTran OBJECT-TYPE
        SYNTAX  INTEGER {
		yes(1),
		no(2)
	}
        ACCESS  read-write
        STATUS  mandatory
        DESCRIPTION
                   " Automatically begin a transaction ( yes(1) ) when a 
		     service request message is received for this service if 
		     the request is not already in transaction mode. " 
        ::=  { tuxTsvcGrpEntry 5 }
 
tuxTsvcGrpLoad OBJECT-TYPE
        SYNTAX  INTEGER (1..32767)
        ACCESS  read-write
        STATUS  mandatory
        DESCRIPTION
                   " This tuxTsvcGrp instance imposes the indicated load on 
		     the system. Service loads are used for load balancing 
		     purposes, that is, queues with higher enqueued workloads 
		     are less likely to be chosen for a new request. "
 
        ::=  { tuxTsvcGrpEntry 6 } 
 
tuxTsvcGrpPrio OBJECT-TYPE
        SYNTAX  INTEGER (1..100)
        ACCESS  read-write
        STATUS  mandatory
        DESCRIPTION
                   " This tuxTsvcGrp object has the indicated dequeuing priority.
		     If multiple service requests are waiting on a queue for 
		     servicing, the higher priority requests will be serviced 
		     first. "
        ::=  { tuxTsvcGrpEntry 7 } 
 
tuxTsvcGrpSvcTimeOut OBJECT-TYPE
        SYNTAX  INTEGER
        ACCESS  read-write
        STATUS  mandatory
        DESCRIPTION
                   " Time limit (in seconds) for processing requests for this 
		     service name.  Servers processing service requests for 
		     this service will be abortively terminated (kill -9) if 
	             they exceed the specified time limit in processing the 
		     request.  A value of 0 for this attribute indicates that 
		     the service should not be abortively terminated. " 
        ::=  { tuxTsvcGrpEntry 8 } 
 
tuxTsvcGrpTranTime OBJECT-TYPE
        SYNTAX  INTEGER
        ACCESS  read-write
        STATUS  mandatory
        DESCRIPTION
                   " Transaction timeout value in seconds for transactions
           	     automatically started for this tuxTsvcGrp instance. 
		     Transactions are started automatically when a request 
		     not in transaction mode is received and the 
		     tuxTsvcGrpAutoTran attribute value for the service is 
		     yes(1). " 
        ::=  { tuxTsvcGrpEntry 9 } 
 
tuxTsvcSrvrLmid OBJECT-TYPE
        SYNTAX  DisplayString (SIZE(1..30))
        ACCESS  read-only
        STATUS  mandatory
        DESCRIPTION
                   " Current logical machine on which an active server offering 
		     this service is running. "
        ::=  { tuxTsvcGrpEntry 10 }
 
tuxTsvcSrvrRqAddr OBJECT-TYPE
        SYNTAX  DisplayString (SIZE(1..30))
        ACCESS  read-only
        STATUS  mandatory
        DESCRIPTION
                   " Symbolic address of the request queue for an active server
           	     offering this service.  See tuxTsrvrRqAddr for more
           	     information on this attribute. "
        ::=  { tuxTsvcGrpEntry 11 }

tuxTsvcSrvrId OBJECT-TYPE
        SYNTAX  INTEGER (0..30000)
        ACCESS  read-write
        STATUS  mandatory
        DESCRIPTION
                   " Server Id of which the service is a part of. During row creation
		     if the value of this provided is zero, the tuxTsvcGrp object is not 
		     activated, else the tuxTsvcGrp instance is activated(advertised)
		     with the server id as provided in tuxTsvcSrvrId, after creation. 
		NOTE:
		     The user can also set the value of this object later to activate
		    (advertise) one or more tuxTsvcGrp instance(s). So the value provided
		    to set this object is actually used to activate another instance of tuxT-
		    svcGrp."
        ::=  { tuxTsvcGrpEntry 12 }
 
tuxTsvcrName OBJECT-TYPE
        SYNTAX  DisplayString (SIZE(1..15))
        ACCESS  read-write
        STATUS  mandatory
        DESCRIPTION
                   " Function name within the associated server assigned to 
		     process requests for this service. 
		     When this object is specified the tuxTsvcGrp instance is activated
		     (advertised). So the user needs to specify the server id of the 
		     corresponding server instance (tuxTsvcSrvrId) in the SNMP index.
		     NOTE: This object can be updated only during row creation."
        ::=  { tuxTsvcGrpEntry 13 }
 
tuxTsvcSrvrNcompleted OBJECT-TYPE
        SYNTAX  INTEGER
        ACCESS  read-only
        STATUS  mandatory
        DESCRIPTION
                   " Number of service requests completed with respect to the
           	     retrieved active or suspended instance since it was 
		     activated (advertised).
           	     Limitation: This attribute is returned only when 
		     tuxTdomainLoadBalance is equal to yes(1)."
        ::=  { tuxTsvcGrpEntry 14 }
 
tuxTsvcSrvrNqueued OBJECT-TYPE
        SYNTAX  INTEGER (0..32767)
        ACCESS  read-only
        STATUS  mandatory
        DESCRIPTION   
                   " Number of requests currently enqueued to this service.  
		     This attribute is incremented at enqueue time and 
		     decremented when the server dequeues the request.

           	     Limitation: This attribute is returned only when the
           	     tuxTdomainModel is set to single-machine(1) and the 
		     tuxTdomainLoadBalance attribute is set to yes(1). "
        ::=  { tuxTsvcGrpEntry 15 }

-- **************************************************************************
-- tuxTlisten group
-- This group represents  runtime  attributes  of  /T
--   listener processes for a distributed application.
-- **************************************************************************

tuxTlistenTbl OBJECT-TYPE
        SYNTAX SEQUENCE OF TuxTlistenEntry
        ACCESS  not-accessible
        STATUS  mandatory
        DESCRIPTION
                  "Runtime attributes of  /T listener processes. "
        ::= { tuxTlisten 1 }

tuxTlistenEntry OBJECT-TYPE
        SYNTAX  TuxTlistenEntry
        ACCESS  not-accessible
        STATUS  mandatory
        DESCRIPTION
                   " A row in tuxTlistenTbl . "
        INDEX { tuxTlistenLmid }
        ::=  { tuxTlistenTbl 1 }

TuxTlistenEntry ::= SEQUENCE {
        tuxTlistenLmid
                DisplayString,
        tuxTlistenState
                INTEGER
	}

tuxTlistenLmid OBJECT-TYPE 
        SYNTAX  DisplayString (SIZE(1..30)) 
        ACCESS  read-only
        STATUS  mandatory    
        DESCRIPTION 
                   " Logical machine identifier. "
        ::=  { tuxTlistenEntry 1 } 

tuxTlistenState OBJECT-TYPE  
        SYNTAX  INTEGER {
		inactive(2),
		active(1)
		} 
        ACCESS  read-only
        STATUS  mandatory     
        DESCRIPTION  
                   " 
          GET: 
               A GET operation will retrieve runtime  information
               for the selected tuxTlisten instance(s).  The follow-
               ing states indicate  the  meaning  of  a  tuxTlistenState
               returned in response to a GET request.  States not
               listed will not be returned.

               inactive(2)  tuxTlisten instance not active.

               active(1)    tuxTlisten instance active.

          SET: 
               This  attribute   is   settable   only   via   the
               tuxTsvcSrvr group . "
        ::=  { tuxTlistenEntry 2 }  

-- *************************************************************************
-- tuxTransaction group
-- This group  represents  runtime  attributes  of active transactions within 
-- the application.
-- *************************************************************************

tuxTranTbl OBJECT-TYPE
        SYNTAX SEQUENCE OF TuxTranEntry
        ACCESS  not-accessible
        STATUS  mandatory
        DESCRIPTION
                  "Runtime attributes of  active transactions . "
        ::= { tuxTransaction 1 }

tuxTranEntry OBJECT-TYPE
        SYNTAX  TuxTranEntry
        ACCESS  not-accessible
        STATUS  mandatory
        DESCRIPTION
                   " A row in tuxTranTbl .

		NOTE:  All objects in this MIB group are local attributes i.e.
		       values for these objects correspond to the local host
		       only, where the TUXEDO agent is running. So the user needs
		       to run an instance of the TUXEDO agent on every node for
		       which these values are of interest."
        INDEX { tuxTranIndx1, tuxTranIndx2, tuxTranIndx3, tuxTranIndx4, tuxTranIndx5 }
        ::=  { tuxTranTbl 1 }

TuxTranEntry ::= SEQUENCE {
        tuxTranCoordLmid
		DisplayString,
        tuxTpTranId
		DisplayString,
        tuxTranXid
		DisplayString,
        tuxTranIndx1
		INTEGER,
        tuxTranIndx2
		INTEGER,
        tuxTranIndx3
		INTEGER,
        tuxTranIndx4
		INTEGER,
        tuxTranIndx5
		INTEGER,
        tuxTranState
		INTEGER,
        tuxTranTimeOut
		INTEGER,
        tuxTranGrpCnt
		INTEGER,
        tuxTranGrpIndex
		INTEGER,
        tuxTranGrpNo
		INTEGER,
        tuxTranGstate
		INTEGER
	}

tuxTranCoordLmid OBJECT-TYPE
     SYNTAX  DisplayString (SIZE(1..30)) 
     ACCESS  read-only
     STATUS  mandatory
     DESCRIPTION 
               "Logical machine identifier of the server group  respon-
                sible for coordinating the transaction. "
     ::= { tuxTranEntry 1 }

tuxTpTranId OBJECT-TYPE
     SYNTAX  DisplayString (SIZE(2..78)) 
     ACCESS  read-only
     STATUS  mandatory
     DESCRIPTION 
               "Transaction identifier as  returned  from  tpsuspend(3)
                mapped  to  a  string representation.  The data in this
                field should not be interpreted directly  by  the  user
                except for equality comparison. "
     ::= { tuxTranEntry 2 }

tuxTranXid OBJECT-TYPE
     SYNTAX  DisplayString (SIZE(2..78)) 
     ACCESS  read-only
     STATUS  mandatory
     DESCRIPTION 
               "Transaction  identifier  as  returned  from  tx_info(3)
                mapped  to  a  string representation.  The data in this
                field should not be interpreted directly  by  the  user
                except for equality comparison. "
     ::= { tuxTranEntry 3 }

tuxTranIndx1 OBJECT-TYPE
     SYNTAX  INTEGER
     ACCESS  read-only
     STATUS  mandatory
     DESCRIPTION 
               " This number is purely for unique indexing of this table."
     ::= { tuxTranEntry 4 }

tuxTranIndx2 OBJECT-TYPE
     SYNTAX  INTEGER
     ACCESS  read-only
     STATUS  mandatory
     DESCRIPTION 
               " This number is purely for unique indexing of this table."
     ::= { tuxTranEntry 5 }

tuxTranIndx3 OBJECT-TYPE
     SYNTAX  INTEGER
     ACCESS  read-only
     STATUS  mandatory
     DESCRIPTION 
               " This number is purely for unique indexing of this table."
     ::= { tuxTranEntry 6 }

tuxTranIndx4 OBJECT-TYPE
     SYNTAX  INTEGER
     ACCESS  read-only
     STATUS  mandatory
     DESCRIPTION 
               " This number is purely for unique indexing of this table."
     ::= { tuxTranEntry 7 }

tuxTranIndx5 OBJECT-TYPE
     SYNTAX  INTEGER
     ACCESS  read-only
     STATUS  mandatory
     DESCRIPTION 
               " This number is purely for unique indexing of this table."
     ::= { tuxTranEntry 8 }

tuxTranState OBJECT-TYPE
     SYNTAX  INTEGER {
		active(1),
		abort-only(2),
		aborted(3),
		com-called(4),
		ready(5),
		decided(6),
		suspended(7)
	} 
     ACCESS  read-write
     STATUS  mandatory
     DESCRIPTION 
               "GET: A  GET operation will retrieve runtime information
               for the  selected  tuxTranTbl  instance(s).   The
               following   states   indicate  the  meaning  of  a
               tuxTranState object.
               States not listed will not be returned.  Note that
               distinct objects pertaining  to  the  same  global
               transaction  (equivalent  transaction identifiers)
               may indicate differing states.   In  general,  the
               state   indicated   on   the   coordinator's  site
               (tuxTranCoorLmid) indicates the  true  state  of  the
               transaction.    The   exception  is  when  a  non-
               coordinator site notices a condition that  transi-
               tions  the  transaction  state to abort-only(2). This
               transition will eventually be  propagated  to  the
               coordinator site and result in the rollback of the
               transaction, but this change may  not  be  immedi-
               ately  reflected  on  the  coordinator  site.

               active(1)       The transaction is active.

               abort-only(2)
			    The transaction has  been  identified
                            for rollback on the retrieval site.

               aborted(3)   The transaction has  been  identified
                            for  rollback  and  rollback has been
                            initiated on the retrieval site.

               com-called(4) 
			    The initiator of the transaction  has
                            called   tpcommit(3)  and  the  first
                            phase of two-phase commit  has  begun
                            on the retrieval site.

               ready(5)     All of the  participating  groups  on
                            the  retrieval site have successfully
                            completed the  first  phase  of  two-
                            phase commit and are ready to be com-
                            mitted.

               decided(6)   The second  phase  of  the  two-phase
                            commit  has  begun  on  the retrieval
                            site.                      

               suspended(7) The initiator of the transaction  has
                            suspended  processing on the transac-
                            tion.  Note that this state  will  be
                            returned  from  the  initiator's site
                            only.

          SET: 
               A SET operation will  update  runtime  information
               for  the  selected tuxTranTbl instance.  The fol-
               lowing states indicate the meaning of  a  tuxTranState
               set  in  a SET request.  States not listed may not
               be set.

               aborted(3)   Abort the  tuxTranTbl  instance  for
                            the    application.    State   change
                            allowed  only  when  in  the  active(1),
                            abort-only(2),  or com-called(4) states.  May
                            not be accompanied  by  a  change  to
                            tuxTranGstate.   Successful return leaves
                            the object in the aborted(3) state. "
     ::= { tuxTranEntry 9 }

tuxTranTimeOut OBJECT-TYPE
     SYNTAX  INTEGER 
     ACCESS  read-only
     STATUS  mandatory
     DESCRIPTION 
               "Time left, in  seconds,  before  the  transaction  will
          timeout  on  the retrieval site.  Note that this attri-
          bute value is returned only when the transaction  state
          is active(1). "
     ::= { tuxTranEntry 10 }

tuxTranGrpCnt OBJECT-TYPE
     SYNTAX  INTEGER 
     ACCESS  read-only
     STATUS  mandatory
     DESCRIPTION 
               "Number of groups  identified  as  participants  in  the
          transaction   by  the  information  returned  from  the
          retrieval site. "
     ::= { tuxTranEntry 11 }

tuxTranGrpIndex OBJECT-TYPE
     SYNTAX  INTEGER 
     ACCESS  read-only
     STATUS  mandatory
     DESCRIPTION 
               "Index of the  first  group  specific  attribute  values
          (tuxTranGrpNo and tuxTranGstate) corresponding to this object."
     ::= { tuxTranEntry 12 }

tuxTranGrpNo OBJECT-TYPE
     SYNTAX  INTEGER 
     ACCESS  read-only
     STATUS  mandatory
     DESCRIPTION 
               "Group number of the participating group. "
     ::= { tuxTranEntry 13 }

tuxTranGstate OBJECT-TYPE
     SYNTAX  INTEGER {
		active(1),
		aborted(2),
		rd-only(3),
		ready(4),
		hcommit(5),
		habort(6),
		done(7),
		pre-prepare(8),
		post-abort(9),
		post-commit(10),
		unknown(11)
	} 
     ACCESS  read-write
     STATUS  mandatory
     DESCRIPTION 
               "A  GET operation will retrieve runtime information
               for   the   selected    tuxTranTbl    instance(s)
              pertaining  to the indicated group.  The following
               states  indicate  the  meaning  of   a   tuxTranGstate
               returned in response to a GET request.  States not
               listed will not be returned.  Note  that  distinct
               objects  pertaining to the same global transaction
               (equivalent transaction identifiers) may  indicate
               differing  states  for individual groups.  In gen-
               eral, the state  indicated  on  the  group's  site
               indicates the true state of the group's participa-
               tion in the transaction.  The  exception  is  when
               the  coordinator site determines that the transac-
               tion should abort and sets each participant  group
               state  to  ABorteD.   This transition will be pro-
               pagated to the group's  site  and  result  in  the
               rollback  of  the  group's work in the transaction
               but may not be reflected immediately.

               active(1)    The  transaction  is  active  in  the
                            indicated group.

               aborted(2)   The transaction has  been  identified
                            for  rollback  and  rollback has been
                            initiated for the indicated group.

               rd-only(3)   The group has successfully  completed
                            the  first  phase of two-phase commit
                            and has performed  only  read  opera-
                            tions  on  the resource manager, thus
                            making it unnecessary to perform  the
                            second   phase  of  commit  for  this
                            group.

               ready(4)     The group has successfully  completed
                            the  first  phase of two-phase commit
			    and is ready to be committed.

               hcommit(5)   The group has been heuristically com-
                            mitted.   This  may  or may not agree
                            with  the  final  resolution  of  the
                            transaction.

               habort(6)    The  group  has  been   heuristically
                            rolled  back.   This  may  or may not
                            agree with the  final  resolution  of
                            the transaction.

               done(7)      This group has completed  the  second
                            phase of the two-phase commit.

	       pre-prepare(8)
			    Indicates that the transaction group contains CORBA 
		servers that have called xa_end (TMSUSPEND) during the course
		of transactional work and that commit processing is beginn-
		ing. This state will exist until either all servers that 
		called xa_end (TMSUSPEND) have caused a call to xa_end 
		(TMSUCESS), at which point the group state will become ready,
		or until one of the target servers does a rollback of the 
		transaction at which point the group state will become either
		post-abort(9) or aborted(2). 

		SUPPORT: CORBA C++ Interface Only.

		post-abort(9)
			   Indicates that an CORBA server called xa_end (TPFAIL)
		and that the TMS has not yet called xa_rollback(). (i.e. 
		that other CORBA servers that had called xa_end (TMSUSPEND) are 
		being notified by the TMS in order to clean up their 
		associated CORBA objects. 

		SUPPORT: CORBA C++ Interface Only

		post-commit(10)
			   Not Implemented yet.

			   SUPPORT: CORBA C++ Interface Only

          SET: 
               A SET operation will  update  runtime  information
               for  the  first  group  in the originating request                             within the  selected  tuxTranTbl  instance.   The
               following   states   indicate  the  meaning  of  a
               tuxTranGstate set in a SET request.  States not listed
               may  not  be  set.   State transitions are allowed
               only when performed within the object representing
               the group's site. 

               hcommit(5)   Heuristically commit the group's work
                            as part of the indicated transaction.
                            State  change   allowed   only   when
                            tuxTranGstate   is   ready,  tuxTranState is
                            ready, and the indicated group is not
                            on  the coordinator's site.  Success-
                            ful return leaves the object  in  the
                            hcommit(5) state.

               habort(6)    Heuristically  rollback  the  group's
                            work  as  part of the indicated tran-
                            saction.  State change  allowed  only
                            when  tuxTranGstat  is  active or ready,
                            tuxTranState is ready, and the  indicated
                            group  is  not  on  the coordinator's
                            site.  Successful return  leaves  the
                            object in the habort state. "
     ::= { tuxTranEntry 14 }


-- *****************************************************************************
-- tuxTnetGroup represents application attributes of network groups. Network
-- groups of LMIDs who can communicate over the networkd address defined in 
-- the tuxTnetMap group. (tuxTnetMapNaddr)
-- *****************************************************************************

tuxTnetGrpTbl OBJECT-TYPE
        SYNTAX SEQUENCE OF TuxTnetGrpEntry
        ACCESS  not-accessible
        STATUS  mandatory
        DESCRIPTION
                  "Attributes of network groups."
        ::= { tuxTnetGroup 1 }

tuxTnetGrpEntry OBJECT-TYPE
        SYNTAX  TuxTnetGrpEntry
        ACCESS  not-accessible
        STATUS  mandatory
        DESCRIPTION
                   " A row in tuxTnetGrpTbl.
		     Row Creation
		     ============
		     A SET request with tuxTnetGrpName, tuxTnetGrpNo and 
		     tuxTnetGrpPrio is required.

		     SUPPORT: This group is only available in TUXEDO 6.4 and 
			   later releases."
        INDEX {  tuxTnetGrpNo }
        ::=  { tuxTnetGrpTbl 1 }

TuxTnetGrpEntry ::= SEQUENCE {
        tuxTnetGrpName
                DisplayString,
        tuxTnetGrpNo
                INTEGER,
        tuxTnetGrpState
                INTEGER,
        tuxTnetGrpPrio
                INTEGER
	}


tuxTnetGrpName OBJECT-TYPE
     SYNTAX  DisplayString (SIZE(1..30))
     ACCESS  read-write
     STATUS  mandatory
     DESCRIPTION 
               " Logical name of network group. A group name is a string of printable
		 characters and cannot contain a pound sign, comma, colon or newline.
		 NOTE: This can be updated only during row creation. "
     ::= { tuxTnetGrpEntry 1 }

tuxTnetGrpNo OBJECT-TYPE
     SYNTAX  INTEGER (1..8191)
     ACCESS  read-write
     STATUS  mandatory
     DESCRIPTION 
               " Group identifier associated with this network group.
		 NOTE: This can be updated only during row creation. "
     ::= { tuxTnetGrpEntry 2 }

tuxTnetGrpState OBJECT-TYPE
     SYNTAX  INTEGER {
		valid(1),
		invalid(2)
		} 
     ACCESS  read-write
     STATUS  mandatory
     DESCRIPTION 
               " A GET request will retrieve configuration information for the selected
		 tuxTnetGrpTbl instance(s). The following states indicate the meaning
		 of tuxTnetGrpState value returned. States not listed will not be returned.

		GET:
		 	valid(1)	: The instance is defined. This is the only valid state
					  for this object.

		SET:
			invalid(2)	: Delete tuxTnetGrpTbl instance from the application."
     ::= { tuxTnetGrpEntry 3 }

tuxTnetGrpPrio OBJECT-TYPE
     SYNTAX  INTEGER (1..8191)
     ACCESS  read-write
     STATUS  mandatory
     DESCRIPTION 
               " The priority band for this network group. All network groups of equivalent band
		 priority will be used in parallel. " 
     ::= { tuxTnetGrpEntry 4 }

-- **************************************************************************************************
-- tuxTnetMap associates tuxTmachineLmids to an instance in tuxTnetGrpTbl. This group identifies
-- which logical machines belong to which network group.
-- **************************************************************************************************

tuxTnetMapTbl OBJECT-TYPE
        SYNTAX SEQUENCE OF TuxTnetMapEntry
        ACCESS  not-accessible
        STATUS  mandatory
        DESCRIPTION
                  ""
        ::= { tuxTnetMap 1 }
 
tuxTnetMapEntry OBJECT-TYPE
        SYNTAX  TuxTnetMapEntry
        ACCESS  not-accessible
        STATUS  mandatory
        DESCRIPTION
                   " A row in tuxTnetMapTbl.
		     Row Creation: A SET request with atleast tuxTnetMapNaddr
		     ============  is needed.

		     SUPPORT: This group is only available in TUXEDO 6.4 and 
			   later releases."
        INDEX {  tuxTnetMapGrpNo , tuxTnetMapLmid }
        ::=  { tuxTnetMapTbl 1 }

TuxTnetMapEntry ::= SEQUENCE {
        tuxTnetMapGrpName
                DisplayString,
        tuxTnetMapGrpNo
                INTEGER,
        tuxTnetMapLmid
                DisplayString,
        tuxTnetMapState
                INTEGER,
        tuxTnetMapNaddr
                DisplayString,
        tuxTnetMapMinEncryptBit
                INTEGER,
        tuxTnetMapMaxEncryptBit
                INTEGER
        }
 
tuxTnetMapGrpName OBJECT-TYPE
     SYNTAX  DisplayString (SIZE(1..30))
     ACCESS  read-only
     STATUS  mandatory
     DESCRIPTION
               " Logical name of network group. A group name is a string of 
		 printable characters and cannot contain a pound sign, comma, 
		 colon or newline."
     ::= { tuxTnetMapEntry 1 }

tuxTnetMapGrpNo OBJECT-TYPE
     SYNTAX  INTEGER (1..8191)
     ACCESS  read-write
     STATUS  mandatory
     DESCRIPTION
               " Identifier for this logical network group. 
                 NOTE: This can be updated only during row creation. "
     ::= { tuxTnetMapEntry 2 }

tuxTnetMapLmid OBJECT-TYPE
     SYNTAX  DisplayString (SIZE(1..30))
     ACCESS  read-write
     STATUS  mandatory
     DESCRIPTION
               " Logical machine name for this network mapping. 
                 NOTE: This can be updated only during row creation. "
     ::= { tuxTnetMapEntry 3 }

tuxTnetMapState OBJECT-TYPE
     SYNTAX  INTEGER {
		valid(1),
		invalid(2)
		} 
     ACCESS  read-write
     STATUS  mandatory
     DESCRIPTION
		" A GET request will retrieve configuration information for the 
		  selected tuxTnetMapTbl instance(s). The following states 
		  indicate the meaning of tuxTnetMapState value returned. States
		  not listed will not be returned.

                GET:
                        valid(1) : 
				The instance is defined. This is the only valid 
				state for this object.

                SET:
                        invalid(2) : 
				Delete tuxTnetMapTbl instance from the applic-
				ation. If any network links were active as a 
				result of the mapping they will be disconnected.
				This disconnection may cause a state change in 
				tuxTBridgeTbl instances associated with the 
				network links. "
     ::= { tuxTnetMapEntry 4 }

tuxTnetMapNaddr OBJECT-TYPE
     SYNTAX  DisplayString (SIZE(1..256))
     ACCESS  read-write
     STATUS  mandatory
     DESCRIPTION
               " Specifies the complete network address to be used by the 
		 BRIDGE process placed on the logical machine as its listening 
		 address.
		 The listening address for a BRIDGE is the means by which it is 
		 contacted by other BRIDGE processes participating in the 
		 application. This attribute must be set if the logical machine 
		 is to participate in a networked application, that is, if the
		 value of tuxTdomainOptions is lan(1) .
		 If the string is of the form `0xhex-digits' or `\\xhex-digits',
		 it must contain an even number of valid hex digits. These 
		 forms are translated internally into a character array conta-
		 ining the hexadecimal representations of the string specified.
		 For TCP/IP addresses either the `//hostname:port' OR 
		 `#.#.#.#:port' format is used."
     ::= { tuxTnetMapEntry 5 }

tuxTnetMapMinEncryptBit OBJECT-TYPE
     SYNTAX  INTEGER {
		none(1),
		enc-40-bit(2),
		enc-128-bit(3),
		unknown(4)
		}
     ACCESS  read-write
     STATUS  mandatory
     DESCRIPTION
               " Wnen establishing a network link to this machine, require at 
		 least this minimum level of encryption. none(1) means no 
		 encryption, while enc-40-bit(2) and enc-128-bit(3) specify the 
		 encryption key length (in bits). If this minimum level of 
		 encryption cannot be met, link establishment will fail. The 
		 default value is none(1).
		 Limitation: Modifications to this object will not affect 
		 established network links. " 
     ::= { tuxTnetMapEntry 6 }

tuxTnetMapMaxEncryptBit OBJECT-TYPE
     SYNTAX  INTEGER {
		none(1),
		enc-40-bit(2),
		enc-128-bit(3),
		unknown(4)
		}
     ACCESS  read-write
     STATUS  mandatory
     DESCRIPTION
               " Wnen establishing a network link , negotiate encryption upto 
		 this level. none(1) means no encryption, while enc-40-bit(2) and 
		 enc-128-bit(3) specify the encryption key length (in bits).  The 
		 default value is enc-128-bit(3).  
		 Limitation: Modifications to this object will not affect 
		 established network links. " 
     ::= { tuxTnetMapEntry 7 }

-- Added : BEGIN-JANUS-NS-TUXEDO7.1-041400

-- **************************************************************************************************
-- tuxTserverCtxt
-- **************************************************************************************************

tuxTserverCtxtTable OBJECT-TYPE
        SYNTAX SEQUENCE OF TuxTserverCtxtEntry
        ACCESS  not-accessible
        STATUS  mandatory
        DESCRIPTION
	"This class represents configuration and runtime attributes of
individual server dispatch contexts within an application. This class is
defined for both single-context and multi-context servers. For
single-context servers, the values in this class are repeated as part of the
tuxTsrvrTbl class. The objects in this group are read-only.

These attribute values provide runtime tracking of statistics and resources
associated with each server dispatch context."
        ::= { tuxTserverCtxt 1 }
 
tuxTserverCtxtEntry OBJECT-TYPE
        SYNTAX  TuxTserverCtxtEntry
        ACCESS  not-accessible
        STATUS  mandatory
        DESCRIPTION
                   " A row in tuxTserverCtxtTable."
        INDEX {  tuxTserverCtxtGrp , tuxTserverCtxtServerID, tuxTserverCtxtContextID }
        ::=  { tuxTserverCtxtTable 1 }

TuxTserverCtxtEntry ::= SEQUENCE {
        tuxTserverCtxtGrp
                DisplayString,
        tuxTserverCtxtServerID
                INTEGER,
        tuxTserverCtxtContextID
                INTEGER,
        tuxTserverCtxtCltLmId
                DisplayString,
        tuxTserverCtxtCltPid
                INTEGER,
        tuxTserverCtxtCltReply
                INTEGER,
        tuxTserverCtxtCmtRet
                INTEGER,
        tuxTserverCtxtCurConv
                INTEGER,
        tuxTserverCtxtCurReq
                INTEGER,
        tuxTserverCtxtCurService
                DisplayString,
        tuxTserverCtxtLastGrp
                INTEGER,
        tuxTserverCtxtSvcTimeOut
                INTEGER,
        tuxTserverCtxtTimeLeft
                INTEGER,
        tuxTserverCtxtTranLev
                INTEGER
        }
 


tuxTserverCtxtGrp OBJECT-TYPE
     SYNTAX  DisplayString (SIZE(1..30))
     ACCESS  read-only
     STATUS  mandatory
     DESCRIPTION
	"Logical Name of the server group. Server group names cannot contain an
	asterisk (*), comma, or colon."
     ::= { tuxTserverCtxtEntry 10 }

tuxTserverCtxtServerID OBJECT-TYPE
     SYNTAX  INTEGER (1..30000)
     ACCESS  read-only
     STATUS  mandatory
     DESCRIPTION
     "Unique (within the server group) server identification number."
     ::= { tuxTserverCtxtEntry 20 }

tuxTserverCtxtContextID OBJECT-TYPE
     SYNTAX  INTEGER (-2..29999)
     ACCESS  read-only
     STATUS  mandatory
     DESCRIPTION
     "Identifier of this particular server context."
     ::= { tuxTserverCtxtEntry 30 }

tuxTserverCtxtCltLmId OBJECT-TYPE
     SYNTAX  DisplayString (SIZE(1..30))
     ACCESS  read-only
     STATUS  mandatory
     DESCRIPTION
     "Logical machine for the initiating client or server. The initiating
     client or server is the process that made the service request that the
     server is currently working on."
     ::= { tuxTserverCtxtEntry 40 }

tuxTserverCtxtCltPid OBJECT-TYPE
     SYNTAX  INTEGER 
     ACCESS  read-only
     STATUS  mandatory
     DESCRIPTION
     "UNIX System process identifier for the initiating client or server.

     Limitation: This is a UNIX system-specific attribute that may not be
     returned if the platform on which the application is being run is not
     UNIX-based."
     ::= { tuxTserverCtxtEntry 50 }

tuxTserverCtxtCltReply OBJECT-TYPE
     SYNTAX  INTEGER {
		yes(1),
		no(2)
		} 
     ACCESS  read-only
     STATUS  mandatory
     DESCRIPTION
     "The initiating client or server is expecting a reply ('yes') or is not
     expecting a reply ('yes')."
     ::= { tuxTserverCtxtEntry 60 }


tuxTserverCtxtCmtRet OBJECT-TYPE
     SYNTAX  INTEGER {
		complete(1),
		logged(2)
		} 
     ACCESS  read-only
     STATUS  mandatory
     DESCRIPTION
     "Setting of the TP_COMMIT_CONTROL characteristic for this server. See
     the description of the BEA Tuxedo ATMI function tpscmt(3c) for details
     on this characteristic."
     ::= { tuxTserverCtxtEntry 70 }

tuxTserverCtxtCurConv OBJECT-TYPE
     SYNTAX  INTEGER 
     ACCESS  read-only
     STATUS  mandatory
     DESCRIPTION
     "Number of conversations initiated by this server via tpconnect() that
     are still active."
     ::= { tuxTserverCtxtEntry 80 }

tuxTserverCtxtCurReq OBJECT-TYPE
     SYNTAX  INTEGER 
     ACCESS  read-only
     STATUS  mandatory
     DESCRIPTION
     "Number of requests initiated by this server via tpcall() or tpacall()
     that are still active."
     ::= { tuxTserverCtxtEntry 90 }

tuxTserverCtxtCurService OBJECT-TYPE
     SYNTAX  DisplayString (SIZE(0..15))
     ACCESS  read-only
     STATUS  mandatory
     DESCRIPTION
     "Service name that the server is currently working on, if any."
     ::= { tuxTserverCtxtEntry 100 }

tuxTserverCtxtLastGrp OBJECT-TYPE
     SYNTAX  INTEGER (1..29999)
     ACCESS  read-only
     STATUS  mandatory
     DESCRIPTION
     "Server group number (tuxTgroupTable: tuxTgroupNo) of the 
	last service request made
     or conversation initiated from this server outward."
     ::= { tuxTserverCtxtEntry 110 }


tuxTserverCtxtSvcTimeOut OBJECT-TYPE
     SYNTAX  INTEGER 
     ACCESS  read-only
     STATUS  mandatory
     DESCRIPTION
     "Server group number (tuxTgroupTable: tuxTgroupNo) of the 
     last service request made
     or conversation initiated from this server outward.
     Time left, in seconds, for this server to process the current service
     request,

     if any. A value of 0 for an active service indicates that no timeout
     processing is being done. See tuxTsvcTbl: tuxTsvcTimeOut for more
     information."
     ::= { tuxTserverCtxtEntry 120 }

tuxTserverCtxtTimeLeft OBJECT-TYPE
     SYNTAX  INTEGER 
     ACCESS  read-only
     STATUS  mandatory
     DESCRIPTION
     "Time left, in seconds, for this server to receive the reply for which
     it is currently waiting before it will timeout. This timeout may be a
     transactional timeout or a blocking timeout."
     ::= { tuxTserverCtxtEntry 130 }

tuxTserverCtxtTranLev OBJECT-TYPE
     SYNTAX  INTEGER 
     ACCESS  read-only
     STATUS  mandatory
     DESCRIPTION
     "Current transaction level for this server. 0 indicates that the server
     is not currently involved in a transaction."
     ::= { tuxTserverCtxtEntry 140 }

-- Added : END-JANUS-NS-TUXEDO7.1-041400

tuxEventTrapVars	OBJECT IDENTIFIER ::= { tuxEvents 6 }

-- ****************************************************************************** 
-- Events MIB 
-- The System Event Monitor feature detects and reports certain pre-defined 
-- events, primarily failures, that a system operator should be aware of. 
-- The Tuxedo SNMP agent on the master node will subscribe to all system events 
-- and generate a corresponding SNMP Trap whenever any of these events is raised. 
-- This MIB defines all the traps which will be generated and the objects which 
-- are passed in the variable bindings for these traps.
-- ****************************************************************************** 


-- tuxEventTrapVars
-- This group contains all objects which are sent as a part of the variable
-- bindings of the traps generated in relation to Tuxedo system events as
-- defined in EVENTS(5)

tuxEventsName OBJECT-TYPE
        SYNTAX  DisplayString 
        ACCESS  read-only 
        STATUS  mandatory
        DESCRIPTION    
                " A string that  uniquely  identifies  this  event.   All
          	  system-generated events begin with `.Sys'. "
        ::= { tuxEventTrapVars 1 }
 

tuxEventsSeverity OBJECT-TYPE
	SYNTAX  INTEGER {
		error(1),
		warn(2),
		info(3)
		}
	ACCESS	read-only 
	STATUS	mandatory
	DESCRIPTION
		" Indicates the severity of the system event." 
	::= { tuxEventTrapVars 2 }

tuxEventsLmid OBJECT-TYPE 
        SYNTAX  DisplayString ( SIZE(1..30) )
        ACCESS  read-only 
        STATUS  mandatory   
        DESCRIPTION     
                " A string identifying the machine where  the  event  was
          	  detected. "
        ::= { tuxEventTrapVars 3 } 
  
tuxEventsTime OBJECT-TYPE 
        SYNTAX  INTEGER 
        ACCESS  read-only 
        STATUS  mandatory   
        DESCRIPTION     
                " A long integer containing the event detection time,  in
          	  seconds,  according  to  the clock on the machine where
          	  detection took place. "
        ::= { tuxEventTrapVars 4 } 
  
tuxEventsUsec OBJECT-TYPE 
        SYNTAX  INTEGER 
        ACCESS  read-only 
        STATUS  mandatory   
        DESCRIPTION     
                " A long integer containing the event detection time,  in
          	  microseconds,  according  to  the  clock on the machine
          	  where detection took place.  While the  units  of  this
          	  value  will  always be microseconds, the actual resolu-
          	  tion depends on the  underlying  operating  system  and
          	  hardware. "
        ::= { tuxEventTrapVars 5 } 
  
tuxEventsDescription OBJECT-TYPE 
        SYNTAX  DisplayString 
        ACCESS  read-only 
        STATUS  mandatory   
        DESCRIPTION     
                " A one-line string summarizing the event. "
        ::= { tuxEventTrapVars 6 } 
  
tuxEventsClass OBJECT-TYPE 
        SYNTAX  DisplayString 
        ACCESS  read-only 
        STATUS  mandatory   
        DESCRIPTION     
                " The class of the  object  associated  with  the  event.
          	  Depending  on  the value of this variable,  the event notification buffer
          	  will contain additional fields specific to an object of
          	  this class. "
        ::= { tuxEventTrapVars 7 } 
  
tuxEventsUlogCat OBJECT-TYPE 
        SYNTAX  DisplayString 
        ACCESS  read-only 
        STATUS  mandatory   
        DESCRIPTION     
                " Catalog name from which the  message  was  derived,  if
          	  any. "
        ::= { tuxEventTrapVars 8 } 
  
tuxEventsUlogMsgNum OBJECT-TYPE
        SYNTAX  INTEGER
        ACCESS  read-only 
        STATUS  mandatory
        DESCRIPTION
                " Catalog message number, if the message was derived from
          	  a catalog. "
        ::= { tuxEventTrapVars 9 } 
 
--- ************************************************************************
--- The following section defines all the traps generated by the Tuxedo SNMP
--- agent when system events are raised.
--- ************************************************************************

--- Domain Related Events 

resourceConfigTrap TRAP-TYPE
	ENTERPRISE tuxedo
	VARIABLES {
		tuxEventsName,
		tuxEventsSeverity,
		tuxEventsLmid,
		tuxEventsTime,
		tuxEventsUsec,
		tuxEventsDescription,
		tuxEventsClass,
		tuxEventsUlogCat,
		tuxEventsUlogMsgNum,
		beaDomainID,
		beaDomainKey,
		beaLogicalAgentName
	}
	DESCRIPTION
      " Format of tuxEventDescription: 
	'INFO: .SysResourceConfig: system configuration change'

        This message indicates that parameters in the tuxTdomain group 
	have been updated. 

	ACTION
	This is an informational message. "
	::= 1

--- Machine related Events.

machineBroadcastTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
	DESCRIPTION
      " Format of tuxEventDescription: 
	'.SysMachineBroadcast: %LMID broadcast delivery failure'

        This message indicates that tpbroadcast() failed for at least for one 
	accesser on LMID of the application.

	ACTION
	Since the broadcast messages are sent in no-blocking mode, it is 
	possible that the process doing the broadcasting encountered a blocking 
	condition and dropped a message. Configure larger message queues and/or 
	load-balance clients/servers such that excessive load is not put on 
	some machines. "
        ::= 2 
 
machineConfigTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
	DESCRIPTION
      " Format of tuxEventDescription: 
	'INFO: .SysMachineConfig: %LMID configuration change '

        This message indicates that parameters in the tuxTmachine group for the 
	given LMID have been updated.

	ACTION
	This is an informational message."
        ::= 3 
 
machineFullMaxAccessersTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
	DESCRIPTION
      " Format of tuxEventDescription: 
	'.SysMachineFullMaxaccessers: %LMID capacity limit'

        This message indicates that the given LMID reached the capacity limit on
	the number of accessers.

	ACTION
	Increase tuxTmachineMaxAccessers for the particular machine or if the 
	hardware/software limits have been reached for the maximum number of 
	users on the machine, move additional users to other machines."
        ::= 4 
 
machineFullMaxConvTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
	DESCRIPTION
      " Format of tuxEventDescription: 
	'.SysMachineFullMaxconv: %LMID capacity limit'

        This message indicates that the given LMID reached the capacity limit 
	on the number of concurrent conversations.

	ACTION
	Increase the value of tuxTmachineMaxConv for the particular machine 
	such that this event is not generated. "
        ::= 5 
 
machineFullMaxGttTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
	DESCRIPTION
      " Format of tuxEventDescription: 
	'.SysMachineFullMaxgtt: %LMID capacity limit '

        This message indicates that the given LMID reached the capacity limit 
	on the number of concurrent transactions.

	ACTION
	Increase the value of tuxTmachineMaxGtt for the particular machine such 
	that this event is not generated."
        ::= 6 
 
machineFullMaxWsClientsTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
	DESCRIPTION
      " Format of tuxEventDescription: 
	'.SysMachineFullMaxwsclients: %LMID capacity limit'

        This message indicates that the given LMID reached the capacity limit 
	on the number of WS clients.

	ACTION
	Increase the value of tuxTmachineMaxWsClients for the particular 
	machine such that this event is not generated. "
        ::= 7 
 
machineMsgQTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
	DESCRIPTION
      " Format of tuxEventDescription: 
	'.SysMachineMsgq: %LMID message queue blocking '

        This message indicates that the server posting a message encountered a 
	blocking condition while putting a message on the message queue.

	ACTION
	Configure larger message queues and/or distribute the load equally on 
	all the machines. "
        ::= 8 
 
machinePartitionedTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
        DESCRIPTION
      " Format of tuxEventDescription: 
	'.SysMachinePartitioned: %LMID is partitioned '

        This message indicates that DBBL partitioned the stated machine either 
	because the BBL on the machine is slow or the network link between the 
	master and the machine is broken. 

	ACTION
	This can be caused due to various reasons. The first one being that the 
	entire network is bogged down due to heavy traffic. The second one is 
	that BBL or BRIDGE on the non-master is either dead or slow. The third 
	one being that the BRIDGE process on the non-master is extremely busy. 
	The software is capable of unpartitioning the machine if things 
	stabilize. "
        ::= 9 
 
machineSlowTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
        DESCRIPTION
      " Format of tuxEventDescription: 
	'.SysMachineSlow: %LMID slow responding to DBBL'

        This message indicates that BBL on the non-master machine is slow in 
	generating IAMOK messages. These messages are sent periodically from 
	BBL's to DBBL which helps DBBL maintain the pulse of the system. 

	ACTION
	This can be caused due to various reasons. The first one being that the 	entire network is bogged down due to heavy traffic. The second one is 
	that BBL on the non-master is either dead or slow. The third one being 
	that the BRIDGE process on the non-master is extremely busy. This 
	problem can be intermittent."
        ::= 10 
 
machineStateTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
        DESCRIPTION
      " Format of tuxEventDescription: 
	'INFO:.SysMachineState: %LMID state change to %STATE'

        This message states that the specified machine changed to a new state 
	as mentioned in tuxEventsDescription.

	ACTION
	This is an informational message."
        ::= 11 

--- TUXEDO network Bridge related Events. 
 
networkConfigTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
        DESCRIPTION
      " Format of tuxEventDescription: 
	'INFO: .SysNetworkConfig: %LMID[0]->%LMID[1] configuration change '

        This message indicates the network link between the two machines 
	specified in tuxEventsDescription changed to a new state.

	ACTION
	This is an informational message. "
        ::= 12 
 
networkDroppedTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
        DESCRIPTION
      " Format of tuxEventDescription: 
	'.SysNetworkDropped: %LMID[0]->%LMID[1] connection dropped '

        This message indicates the network link between the two machines 
	specified was dropped abnormally.

	ACTION
	It can happen either because the BRIDGE on either machine died or one 
	of the machines crashed. "
        ::= 13 
 
networkFailureTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
        DESCRIPTION
      " Format of tuxEventDescription: 
	'.SysNetworkFailure: %LMID[0]->%LMID[1] connection failure '

        This message indicates the BRIDGE process on TA_LMID[0] could not make 
	a network connection to BRIDGE process on TA_LMID[1].

	ACTION
	It can happen either because the BRIDGE on remote machine died or the 
	remote machine itself crashed." 
        ::= 14 
 
networkFlowTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
        DESCRIPTION
      " This trap is generated when `.SysNetworkFlow' event is generated."
        ::= 15 
 
networkStateTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
        DESCRIPTION
      " Format of tuxEventDescription: 
	'INFO: .SysNetworkState: %LMID[0]->%LMID[1] state change to %STATE '

        This message states that the virtual circuit between machines TA_LMID[0]
	and TA_LMID[1] changed to a new state as mentioned in the message.

	ACTION
	This is an informational message. "
        ::= 16 

--- TUXEDO Server related events
 
serverCleaningTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
        DESCRIPTION
      " Format of tuxEventDescription: 
	'.SysServerCleaning: %SERVERNAME, group %SRVGRP, id %SRVID server 
	  cleaning '

        This message indicates that the server specified above died abnormally 
	and BBL cleaned up the slot allocated by the server. 

	ACTION
	Debug the server and fix the problem before it is restarted again. " 
        ::= 17 
 
serverConfigTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
        DESCRIPTION
      " Format of tuxEventDescription: 
	'INFO: .SysServerConfig: %SERVERNAME, group %SRVGRP, id %SRVID 
		configuration change '

        This message indicates that the configuration parameters for server 
	specified above have been updated.

	ACTION
	This is an informational message. "
        ::= 18 
 
serverDiedTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
        DESCRIPTION
      " Format of tuxEventDescription: 
	'.SysServerDied: %SERVERNAME, group %SRVGRP, id %SRVID server died '

        This message indicates that the server specified above died abnormally 
	and BBL detected this condition in its periodic scan of the BB. 
	ACTION
	Debug the server and fix the problem before it is restarted again. "
        ::= 19 
 
serverInitTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
        DESCRIPTION
      " Format of tuxEventDescription: 
	'.SysServerInit: %SERVERNAME, group %SRVGRP, id %SRVID server 
			 initialization failure '

        This message indicates that the server specified above failed in 
	tpsvrinit() and therefore could not be booted. 

	ACTION
	Fix the problem and then reboot the server. It can be due to a TUXEDO 
	resource limit or an application-specific problem. "
        ::= 20 
 
serverMaxgenTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
        DESCRIPTION
      " Format of tuxEventDescription: 
	'.SysServerMaxgen: %SERVERNAME, group %SRVGRP, id %SRVID exceeded 
	  		   MAXGEN restart limit '

        This message indicates that the server specified above died abnormally 
	and since this has been marked as a restartable server, it has been 
	restarted (MAXGEN-1) times in the specified GRACE period. 

	ACTION
	TUXEDO application servers should not ordinarily die abnormally. It is 
	most likely due to a application-specific problem. Debug the server 
	and resolve the problem before restarting it again. "
        ::= 21 
 
serverRestartingTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
        DESCRIPTION
      " Format of tuxEventDescription: 
	'.SysServerRestarting: %SERVERNAME, group %SRVGRP, id %SRVID restarting'

        This message indicates that the server specified above died abnormally 
	and since this has been marked as a restartable server, it has been 
	restarted. 

	ACTION
	TUXEDO application servers should not ordinarily die abnormally. It is 
	most likely due to a application-specific problem. Debug the server and 
	resolve the problem before restarting it again." 
        ::= 22 
 
serverStateTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
        DESCRIPTION
      " Format of tuxEventDescription: 
	'INFO: .SysServerState: %SERVERNAME, group %SRVGRP, id %SRVID state 
				change to %STATE '

        This message indicates that the server specified above changed to a new 
	state.

	ACTION
	This an informational message. "
        ::= 23 
 
serverTpExitTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
        DESCRIPTION
      " Format of tuxEventDescription: 
	'INFO: .SysServerTpexit: %SERVERNAME, group %SRVGRP, id %SRVID 
				 requested TPEXIT '

        This message indicates that the server specified above received a 
	request and the service routine code did a tpreturn(TPEXIT) while the 
	server was executing application-specific code. 

	ACTION
	This an informational message. "
        ::= 24 

--- Tuxedo Client related Events
 
clientConfigTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
        DESCRIPTION
      " Format of tuxEventDescription: 
	'INFO: .SysClientConfig: User %USRNAME on %LMID configuration change '

        This message indicates that the attributes on the client specified 
	above have been changed.

	ACTION
	This an informational message. "
        ::= 25 
 
clientDiedTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        }
        DESCRIPTION
      " Format of tuxEventDescription: 
	'.SysClientDied: User %USRNAME on %LMID client died '

        This message indicates that the client specified above exited the 
	application without doing a tpterm().  In the normal way, the clients 
	should do a tpterm() before exiting the application. 

	ACTION
	This an informational message." 
        ::= 26 
 
clientSecurityTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
        DESCRIPTION
      " Format of tuxEventDescription: 
	'User %USRNAME on %LMID authentication failure' 

	This message indicates that the client specified above failed security 
	validation when trying to join the application.

	ACTION
	Check to make sure that this is not some hacker trying to gain access 
	to your application data. "
        ::= 27 
 
clientStateTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
        DESCRIPTION
      " Format of tuxEventDescription: 
	'User %USRNAME on %LMID state change to %STATE '

	This message indicates that the client specified above changed to a new 
	state.

	ACTION
	This an informational message. "
        ::= 28 

--- Transaction related Events
 
transHeuristicAbortTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
        DESCRIPTION
      " Format of tuxEventDescription: 
	'Transaction %GTRID in group %GRPNO'

	This message indicates that the database in group specified above 
	performed heuristic abort on the transaction indicated in the message. 

	ACTION
	Check to make sure that the coordinator of the transaction is still up 
	and running. "
        ::= 29 
 
transHeuristicCommitTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
        DESCRIPTION
      " Format of tuxEventDescription: 'Transaction %GTRID in group %GRPNO'

	This message indicates that the database in group specified above 
	performed heuristic commit on the transaction indicated in the message. 

	ACTION
	Check to make sure that the coordinator of the transaction is still 
	up and running. "
        ::= 30 

--- Events related to TUXEDO Event system. 
 
eventDeliveryTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
        DESCRIPTION
      " Format of tuxEventDescription: 
	'System Event Monitor delivery failure on %LMID '

	This message indicates that the event server failed to perform at least 
	one notification for a posted event. 

	ACTION
	Check to make sure that the notifications specified in the subscriptions
	that match the posted event are doable. "
        ::= 31 
 
eventFailureTrap TRAP-TYPE
        ENTERPRISE tuxedo
        VARIABLES {  
                tuxEventsName,
                tuxEventsSeverity,
                tuxEventsLmid,   
                tuxEventsTime, 
                tuxEventsUsec, 
                tuxEventsDescription, 
                tuxEventsClass,   
                tuxEventsUlogCat, 
                tuxEventsUlogMsgNum,
		beaDomainID,
		beaDomainKey,
		beaLogicalAgentName
        } 
        DESCRIPTION
      " Format of tuxEventDescription: 
	'System Event Monitor subsystem failure on %LMID '

	The system event server periodically sends a message to it self to 
	detect blocking conditions on the message queues. This event is 
	generated if the server can't put a message on the queue in no-block 
	mode. It can also be generated if the received message doesn't match 
	what sent out earlier. The second case will probably never happen. 

	ACTION
	Configure larger message queues or distribute the load in the 
	application equally among all the machines. "
        ::= 32 

--******************************************************************************
-- tuxFactory group
-- This represents occurrences of factories registered with the FactoryFinder. 
-- The available factories for the application are reflected in this MIB and 
-- can be shown to the administrator via the GUI or command-line tools. Scope 
-- is global.
--******************************************************************************

tuxFactoryTable OBJECT-TYPE
        SYNTAX  SEQUENCE OF tuxFactoryEntry
        ACCESS  not-accessible
        STATUS  mandatory
        DESCRIPTION
 		  "This table represents occurrences of factories registered 
		   with the FactoryFinder. "
        ::= { tuxedo 48 }

tuxFactoryEntry OBJECT-TYPE
        SYNTAX tuxFactoryEntry
        ACCESS  not-accessible
        STATUS  mandatory
        DESCRIPTION
                  " A row in tuxFactoryTable."
        INDEX { tuxFactorySerNo }
        ::= { tuxFactoryTable 1 }

tuxFactoryEntry ::= SEQUENCE {
   tuxFactorySerNo
        INTEGER,
   tuxFactoryID
        DisplayString,
   tuxFactoryIfName
        DisplayString,
   tuxFactoryState
        INTEGER
   }

tuxFactorySerNo OBJECT-TYPE 
        SYNTAX  INTEGER
        ACCESS  read-only
        STATUS  mandatory    
        DESCRIPTION 
                  " This object is running number used an index to this table."
        ::= { tuxFactoryEntry 1 } 
 
tuxFactoryID OBJECT-TYPE 
	SYNTAX  DisplayString (SIZE (1..256))
        ACCESS  read-only
        STATUS  mandatory    
        DESCRIPTION 
                  " The registered ID for the factory "
        ::= { tuxFactoryEntry 2 } 

tuxFactoryIfName OBJECT-TYPE 
        SYNTAX  DisplayString (SIZE (1..128))
        ACCESS  read-only
        STATUS  mandatory    
        DESCRIPTION 
                  " The fully qualified interface name for the factory. The 
		    interface repository id for the factory. The format of 
		    this name is dependent on the options specified in the 
		    IDL which generates the interface implementation. See 
		    CORBA 2.1 Specification Section 7.6 for details."
        ::= { tuxFactoryEntry 3 } 

tuxFactoryState OBJECT-TYPE 
        SYNTAX	INTEGER {
		active(1)
		} 
        ACCESS  read-only
        STATUS  mandatory     
        DESCRIPTION  
                  " 
          Value returned on GET request:
	  -----------------------------
               A GET operation will retrieve runtime  information
               for  the  selected  tuxFactoryTable instance(s).

               active(1)    The tuxFactoryTable instance is registered with 
			    the FactoryFinder."
        ::= { tuxFactoryEntry 4 }  

--******************************************************************************

tuxInterfaceInfo OBJECT IDENTIFIER ::= { tuxedo 53 }
--******************************************************************************
-- tuxInterfaceTable
-- This represents configuration and runtime attributes of CORBA interfaces at 
-- both the domain and server group levels.
--******************************************************************************

tuxInterfaceTable OBJECT-TYPE
        SYNTAX  SEQUENCE OF tuxInterfaceEntry
        ACCESS  not-accessible
        STATUS  mandatory
        DESCRIPTION
      " This table represents configuration and runtime attributes 
	of CORBA interfaces at both the domain and server group levels. "
        ::= { tuxInterfaceInfo 1 }

tuxInterfaceEntry OBJECT-TYPE
        SYNTAX tuxInterfaceEntry
        ACCESS  not-accessible
        STATUS  mandatory
        DESCRIPTION
        " A row in tuxInterfaceTable.
   This table represents configuration and runtime attributes of CORBA interf-
   aces at both the domain and server group levels.
   A domain-level tuxInterfaceTable instance is one that is not associated with
   a Server Group. Its tuxIfSrvGrp attribute has the (invalid) value '*'.
 
   A server group level tuxInterfaceTable instance is one that has an associated
   server group (i.e., its tuxIfSrvGrp attribute contains a valid server group
   name for the domain). This Server Group level representation of an interface
   also provides a container for managing interface state (tuxIfState) and for
   collecting accumulated statistics.
 
   An associated server group level tuxInterfaceTable instance must exist for 
   any CORBA Interfaces that are activated in a server. The activation of 
   interfaces in a server is controlled by the state of a tuxIfQueue instance 
   for the interface. Activation of a tuxIfQueue instance causes its attributes
   to be initialized with the values specified for the associated server group 
   level tuxInterfaceTable instance. If such an object does not exist, then one
   will be dynamically created. This dynamically-created server group level 
   tuxInterfaceTable instance will be initialized with the attributes of the 
   domain level tuxInterfaceTable instance for the interface if one exists.  If
   an associated domain level tuxInterfaceTable instance does not exist, system
   specified default configuration values will be applied.  Once activated, 
   interfaces are always associated with a server group level tuxInterfaceTable
   instance.
  
   The specification of configuration attributes for interfaces at any level is
   completely optional, system defined default values will be provided and
   runtime server group level tuxInterfaceTable instances will be created.  
   Interfaces to be offered by a server are identified via the ICF file used to
   generate server skeletons and advertised automatically by the system at
   server activation time. 

   Row Creation: The user needs to do a SET request with atleast tuxIfName and
   ============  tuxIfSrvGrp. "

        INDEX { tuxIfSerNo }
        ::= { tuxInterfaceTable 1 }

tuxInterfaceEntry ::= SEQUENCE {
   tuxIfSerNo
        INTEGER,
   tuxIfName
        DisplayString,
   tuxIfSrvGrp
        DisplayString,
   tuxIfState
        INTEGER,
   tuxIfAutoTran
        INTEGER,
   tuxIfLoad
        INTEGER,
   tuxIfPrio
        INTEGER,
   tuxIfTimeout
        INTEGER,
   tuxIfTranTime
        INTEGER,
   tuxIfFbRoutingName
        DisplayString,
   tuxIfLmid
        DisplayString,
   tuxIfNumServers
        INTEGER,
   tuxIfTpPolicy
        INTEGER,
   tuxIfTxPolicy
        INTEGER
   }

 
tuxIfSerNo OBJECT-TYPE 
        SYNTAX  INTEGER
        ACCESS  read-only
        STATUS  mandatory    
        DESCRIPTION 
      " This object is running number used an index to this table."
        ::= { tuxInterfaceEntry 1 } 

tuxIfName OBJECT-TYPE 
        SYNTAX  DisplayString (SIZE (1..128))
        ACCESS  read-write
        STATUS  mandatory    
        DESCRIPTION 
                  " The fully qualified interface name. The interface repository 
		    id for the interface. The format of this name is dependent 
		    on the options specified in the IDL which generates the 
		    interface implementation. See CORBA 2.1 Specification 
		    Section 7.6 [CORBA] for details. 
		    NOTE: This object can be SET only during creation of a new row."
        ::= { tuxInterfaceEntry 2 } 

tuxIfSrvGrp OBJECT-TYPE 
        SYNTAX  DisplayString (SIZE (0..30))
        ACCESS  read-write
        STATUS  mandatory    
        DESCRIPTION 
                  " Server group name.  Server group names cannot contain an 
		    asterisk, comma or colon.  An explicitly specified '*' value 		    for this abject is used to specify and query domain level 
		    configuration and runtime information for an interface.  
		    There are certain limitations and semantic differences 
		    noted in other objects with respect to domain and group 
		    level objects in tuxInterfaceTable.
		    NOTE: This object can be SET only during creation of a new row."
        ::= { tuxInterfaceEntry 3 } 

tuxIfState OBJECT-TYPE 
        SYNTAX  INTEGER {
		active(1),
		inactive(2),
		suspended(3),
		partitioned(4),
		invalid(5),
		reactivate(6),
		unknown(7)
	}
        ACCESS  read-write
        STATUS  mandatory    
        DESCRIPTION 
                  " Following are the semantics for tuxIfState values for GET and 
	SET requests. Where semantics differ between group and domain level 
	objects, those differences are noted.

	GET: {active | inactive | suspended | partitioned}
	A GET request will retrieve configuration information for the selected 
	tuxInterfaceTable instance(s). 
	States not listed will not be returned. 

	active(1): tuxInterfaceTable instance is defined and at least one 
	corresponding tuxIfQueueTable instance is in the active state. 

	For a group level tuxInterfaceTable instance, corresponding 
	tuxIfQueueTable instances are those with matching tuxIfname and 
	tuxIfSrvGrp objects.  
	For a domain level tuxInterfaceTable instance, corresponding 
	tuxIfQueueTable instances are those with matching tuxIfName value 
	regardless of their tuxIfSrvGrp value.

	inactive(2): tuxInterfaceTable instance is defined and there are no 
	corresponding tuxIfQueueTable instances in any active equivalent state.

	suspended(3): tuxInterfaceTable instance is defined and amongst all 
	corresponding  tuxIfQueueTable instances there are none in the active 
	state and at least one in the suspended state.

	partitioned(4): tuxInterfaceTable instance is defined and amongst all 
	corresponding  tuxIfQueueTable instances there are 
		a) none in the active state, 
		b) none in the suspended state and 
		c) at least one in the partitioned state.  

	SET: { invalid | active | reactivate | suspended}
	A SET request will update configuration and runtime information for the 
	selected tuxInterfaceTable instance. Note that modifications may affect 
	more than one server group when making domain level changes and runtime 
	modifications may affect more than one server if multiple servers are 
	currently offering an interface.

	invalid(5): Delete tuxInterfaceTable instance for application. State 
	change only allowed when in the inactive(2) state.

	active(1): Activate the tuxInterfaceTable instance. Setting this state on 
	the domain level object has the effect of activating all corresponding 
	tuxIfQueueTable instances that are currently suspended throughout the 
	domain.  Setting this state on the group level object will affect only 
	servers within the group offering the interface.  State change only 
	allowed when in the suspended state. Successful return leaves object in 
	active(1) state.

	reactivate(6): Reactivate the tuxInterfaceTable instance. Setting this 
	state on the domain level object has the effect of activating all 
	corresponding tuxIfQueueTable instances that are currently suspended 
	throughout the domain.  Setting this state on the group level object 
	will affect only servers within the group offering the interface.  State 
	change only allowed when in the active(1) or suspended(3) states. Succe-
	ssful return leaves object in active(1) state. This state permits global 
	activation of tuxIfQueueTable instances suspended at the group level 
	without having to individually activate each group level tuxInterfaceTable
	instance .

	suspended(3): Suspend the tuxInterfaceTable instance. Setting this state 
	on the domain level object has the effect of suspending all corresponding
	tuxIfQueueTable instances that are currently active throughout the domain.
	Setting this state on the group level object will affect only servers 
	within the group offering the interface.  State change only allowed when 
	in the active(1) state.  Successful return leaves object in suspended(3)
 	state.

	Limitation: Dynamic advertisement of interfaces (i.e., state change from 
	inactive(2) or invalid(5) to active(1)) is not supported, nor is 
	unadvertisement (i.e., state change from active(1) to inactive(1))." 

        ::= { tuxInterfaceEntry 4 } 

tuxIfAutoTran OBJECT-TYPE 
        SYNTAX  INTEGER {
		yes(1),
		no(2)
	}
        ACCESS  read-write
        STATUS  mandatory
        DESCRIPTION
                  "Signifies whether a transaction will be automatically started 
	for invocations made outside a transaction context. 

	Limitations: 

	1. Runtime updates to this attribute are not reflected in active 
	   equivalent tuxInterfaceTable instances.
	
	2. tuxIfTxPolicy may override the value specified for this attribute in 
	   the ubbconfig file. If tuxIfTxPolicy is:
	
		always(1) - a value of no(2) will have no effect at runtime. 
		Behavior will be as though the setting was yes(1).
		never(2) - a value of yes(1) will have no effect. The interface 
		will never be involved in a transaction.
		ignore(3) - a value of yes(1) will have no effect. The interface 
		will never be involved in a transaction. "
        ::= { tuxInterfaceEntry 5 } 

tuxIfLoad OBJECT-TYPE 
        SYNTAX  INTEGER (1..32767)
        ACCESS  read-write
        STATUS  mandatory    
        DESCRIPTION 
                  " This object imposes the indicated load on the system. 
	Interface loads are used for load balancing purposes, that is, queues 
	with higher enqueued workloads are less likely to be chosen for a new 
	request.

	Limitation: Runtime updates to this attribute for domain level objects 
	will not affect corresponding group level objects for the same 
	interface."
        ::= { tuxInterfaceEntry 6 } 

tuxIfPrio OBJECT-TYPE 
        SYNTAX  INTEGER (1..100)
        ACCESS  read-write
        STATUS  mandatory    
        DESCRIPTION 
                  " This object has the indicated dequeuing priority. If 
	multiple interface requests are waiting on a queue for servicing, the 
	higher priority requests will be handled first. 

	Limitation: Runtime updates to this attribute for domain level objects 
	will not affect corresponding group level objects for the same 
	interface. "
        ::= { tuxInterfaceEntry 7 } 

tuxIfTimeout OBJECT-TYPE 
        SYNTAX  INTEGER
        ACCESS  read-write
        STATUS  mandatory    
        DESCRIPTION 
                  " Time limit (in seconds) for processing individual method 
	invocations for this interface.  Servers processing method invocations 
	for this interface will be abortively terminated if they exceed the 
	specified time limit in processing the request.  A value of 0 for this 
	attribute indicates that the server should not be abortively terminated. 

	Limitation: Runtime updates to this attribute for domain level objects
	will not affect corresponding group level objects for the same 
	interface. "
        ::= { tuxInterfaceEntry 8 } 

tuxIfTranTime OBJECT-TYPE 
        SYNTAX  INTEGER
        ACCESS  read-write
        STATUS  mandatory    
        DESCRIPTION 
      " Transaction timeout value in seconds for transactions automatically 
	started for this tuxInterfaceTable instance.  Transactions are started 
	automatically when a requests not in transaction mode is received and 
	the tuxIfAutoTran object value for the interface is yes(1). 

	Limitation: Runtime updates to this attribute for domain level objects 
	will not affect corresponding group level objects for the same 
	interface."
        ::= { tuxInterfaceEntry 9 } 

tuxIfFbRoutingName OBJECT-TYPE 
        SYNTAX  DisplayString (SIZE(1..15))
        ACCESS  read-write
        STATUS  mandatory    
        DESCRIPTION 
      " The factory-based routing criteria associated with this interface.  

	Limitation: This attribute may be set only for a domain level tuxInter-
	faceTable instance, i.e., tuxIfSrvGrp is '*'."
        ::= { tuxInterfaceEntry 10 } 

tuxIfLmid OBJECT-TYPE 
        SYNTAX  DisplayString (SIZE(1..30))
        ACCESS  read-only
        STATUS  mandatory    
        DESCRIPTION 
      " Current logical machine with which the active equivalent group level 
	tuxInterfaceTable instance is associated.  This attribute is NULL, for 
	domain level objects. "
        ::= { tuxInterfaceEntry 11 } 

tuxIfNumServers OBJECT-TYPE 
        SYNTAX  INTEGER
        ACCESS  read-only
        STATUS  mandatory    
        DESCRIPTION 
      " Number of corresponding servers offering this interface. "
        ::= { tuxInterfaceEntry 12 } 

tuxIfTpPolicy OBJECT-TYPE 
        SYNTAX  INTEGER {
		method(1),
		transaction(2),
		process(3)
	}
        ACCESS  read-only
        STATUS  mandatory    
        DESCRIPTION 
      " The TP framework deactivation policy. This reflects the policy 
	registered with the framework at server startup. The first server to 
	register the interface sets the value in tuxInterfaceTable. This value 
	cannot be changed."
        ::= { tuxInterfaceEntry 13 } 

tuxIfTxPolicy OBJECT-TYPE 
        SYNTAX  INTEGER {
		always(1),
		never(2),
		optional(3),
		ignore(4)
	}
        ACCESS  read-only
        STATUS  mandatory    
        DESCRIPTION 
      " The transaction policy for the interface. The setting in this attribute 
	affects the effect of the tuxIfAutoTran object. See Description of 
	tuxIfAutoTran for further explanation.  It is set by the developer when 
	the server is built and registered at server startup."
        ::= { tuxInterfaceEntry 14 } 

-- ****************************************************************************
-- tuxLclInterfaceTbl
-- This table returns the Local attributes in tuxInterfaceTable for the local 
-- host on which the Agent Connection is running. 
-- ****************************************************************************

tuxLclInterfaceTable OBJECT-TYPE
        SYNTAX  SEQUENCE OF tuxLclInterfaceEntry
        ACCESS  not-accessible
        STATUS  mandatory
        DESCRIPTION
      " This table returns the Local attributes in tuxInterfaceTable for the
	local host on which the Agent Connection is running." 
        ::= { tuxInterfaceInfo 2 }
 
tuxLclInterfaceEntry OBJECT-TYPE
        SYNTAX tuxLclInterfaceEntry
        ACCESS  not-accessible
        STATUS  mandatory
        DESCRIPTION
      " This table returns the Local attributes in tuxInterfaceTable for the
	local host on which the Agent Connection is running." 
	INDEX { tuxLclIfSerNo }
	::= { tuxLclInterfaceTable 1 }

tuxLclInterfaceEntry ::= SEQUENCE {
   tuxLclIfSerNo
	INTEGER,
   tuxLclIfName
	DisplayString,
   tuxLclIfSrvGrp
	DisplayString,
   tuxLclIfNcompleted
        INTEGER,
   tuxLclIfNqueued
        INTEGER
}

tuxLclIfSerNo OBJECT-TYPE
        SYNTAX  INTEGER
        ACCESS  read-only
        STATUS  mandatory
        DESCRIPTION
      " This object is running number used an index to this table."
        ::= { tuxLclInterfaceEntry 1 }
 
tuxLclIfName OBJECT-TYPE
        SYNTAX  DisplayString (SIZE (1..128))
        ACCESS  read-only
        STATUS  mandatory
        DESCRIPTION
                  " The fully qualified interface name. The interface repository
                    id for the interface. The format of this name is dependent
                    on the options specified in the IDL which generates the
                    interface implementation. See CORBA 2.1 Specification
                    Section 7.6 [CORBA] for details. "
        ::= { tuxLclInterfaceEntry 2 }
 
tuxLclIfSrvGrp OBJECT-TYPE
        SYNTAX  DisplayString (SIZE (0..30))
        ACCESS  read-only
        STATUS  mandatory
        DESCRIPTION
                  " Server group name.  Server group names cannot contain an
                    asterisk, comma or colon.  An explicitly specified '*' value
                    for this object indicates a domain level interface."
        ::= { tuxLclInterfaceEntry 3 }

tuxLclIfNcompleted OBJECT-TYPE
        SYNTAX  INTEGER
        ACCESS  read-only
        STATUS  mandatory
        DESCRIPTION
                  " Number of interface method invocations completed with respect
	to the corresponding tuxIfQueueTable instances since they were initially 
	offered. The values returned are for the indicated interface on the 
	localhost where the Agent Connection is running.
        Limitation: This attribute is returned only when tuxTdomainLoadBalance is 
	equal to yes(1)."
        ::= { tuxLclInterfaceEntry 4 }

tuxLclIfNqueued OBJECT-TYPE
        SYNTAX  INTEGER
        ACCESS  read-only
        STATUS  mandatory
        DESCRIPTION
                  " Number of requests currently enqueued for this interface. 
	The values returned are for the indicated interface on the localhost
	where the Agent Connection is running.
        Limitation: This attribute is returned only when tuxTdomainLoadBalance is 
	equal to yes(1)."
        ::= { tuxLclInterfaceEntry 5 }

--******************************************************************************
-- tuxIfQueueTable
-- The tuxIfQueueTable group represents runtime attributes of an interface as it 
-- pertains to a particular server queue (tuxTqueue).
--******************************************************************************
 
tuxIfQueueTable OBJECT-TYPE
        SYNTAX  SEQUENCE OF tuxIfQueueEntry
        ACCESS  not-accessible
        STATUS  mandatory
        DESCRIPTION
  "The tuxIfQueueTable group represents runtime attributes of an interface as it 
   pertains to a particular server queue (tuxTqueue). This is primarily a 
   read-only group providing access to the inherited configuration attributes of 
   an interface as well as statistics relating to the interface on the queue. 
   Additionally, this class gives administrators finer granularity in suspending 
   and activating interfaces. This class provides the link between an interface 
   name and the server processes capable of processing method invocations on the 
   interface, i.e., tuxIfQRqAddr can be used to identify the corresponding servers 
   in tuxTsrvrTbl and tuxTsrvrTblExt groups. "
        ::= { tuxInterfaceInfo 3 }
 
tuxIfQueueEntry OBJECT-TYPE
        SYNTAX tuxIfQueueEntry
        ACCESS  not-accessible
        STATUS  mandatory
        DESCRIPTION
        " A row in tuxIfQueueTable."
        INDEX { tuxIfQueueSerNo }
        ::= { tuxIfQueueTable 1 }
 
tuxIfQueueEntry ::= SEQUENCE {
   tuxIfQueueSerNo
        INTEGER,
   tuxIfQueueName
        DisplayString,
   tuxIfQueueSrvGrp
        DisplayString,
   tuxIfQueueRqAddr
        DisplayString,
   tuxIfQueueState
        INTEGER,
   tuxIfQueueAutoTran
        INTEGER,
   tuxIfQueueLoad
        INTEGER,
   tuxIfQueuePrio
        INTEGER,
   tuxIfQueueTimeout
        INTEGER,
   tuxIfQueueTranTime
        INTEGER,
   tuxIfQueueFbRoutingName
        DisplayString,
   tuxIfQueueLmid
        DisplayString,
   tuxIfQueueNumServers
        INTEGER,
   tuxIfQueueTpPolicy
        INTEGER,
   tuxIfQueueTxPolicy
        INTEGER
   }
 
 
tuxIfQueueSerNo OBJECT-TYPE
        SYNTAX  INTEGER
        ACCESS  read-only
        STATUS  mandatory
        DESCRIPTION
      " This object is running number used an index to this table."
        ::= { tuxIfQueueEntry 1 }
 
tuxIfQueueName OBJECT-TYPE
        SYNTAX  DisplayString (SIZE (1..128))
        ACCESS  read-only
        STATUS  mandatory
        DESCRIPTION
                  " The fully qualified interface name. The interface repository
                    id for the interface. The format of this name is dependent
                    on the options specified in the IDL which generates the
                    interface implementation. See CORBA 2.1 Specification
                    Section 7.6 [CORBA] for details. "
        ::= { tuxIfQueueEntry 2 }

tuxIfQueueSrvGrp OBJECT-TYPE
        SYNTAX  DisplayString (SIZE (1..30))
        ACCESS  read-only
        STATUS  mandatory
        DESCRIPTION
      " Server group name. Server group names cannot contain an asterisk, comma 
	or colon. "
        ::= { tuxIfQueueEntry 3 }

tuxIfQueueRqAddr OBJECT-TYPE
        SYNTAX  DisplayString (SIZE (1..30))
        ACCESS  read-only
        STATUS  mandatory
        DESCRIPTION
      " Symbolic address of the request queue for an active server offering this 
	interface. See tuxTsrvrRqAddr for more information on this attribute."
        ::= { tuxIfQueueEntry 4 }

tuxIfQueueState OBJECT-TYPE
        SYNTAX  INTEGER {
		active(1),
		suspended(2),
		partitioned(3),
		unknown(4)
	}
        ACCESS  read-write
        STATUS  mandatory
        DESCRIPTION
      " GET: {active | suspended | partitioned} 
	A GET request will retrieve configuration information for the selected 
	tuxIfQueueTable instances. The following states indicate the meaning of 
	a tuxIfQueueState value returned in response to a GET request. States not 
	listed will not be returned. 

 	active(1)  
		represents an available interface in the running system. 
 
	suspended(2)
 		represents a currently suspended interface in the running system. 
 
	partitioned(3)
 		represents a currently partitioned interface in the running 
		system. 
 
	SET: { active | suspended} 

 	active(1) 
 		Activate the tuxIfQueueTable instance. State change only allowed 
		when in the suspended(2) state. Successful return leaves instance
		in active(1) state. 
 
	suspended(2) 
 		Suspend the tuxIfQueueTable instance. State change only allowed 
		when in the active(1) state. Successful return leaves object in 
		suspended(2) state. 

	Limitation: Dynamic advertisement of interfaces (i.e., state change from 
	inactive or invalid to active) is not supported, nor is unadvertisement 
	(i.e., state change from active to inactive). "
        ::= { tuxIfQueueEntry 5 }

tuxIfQueueAutoTran OBJECT-TYPE
        SYNTAX  INTEGER {
		yes(1),
		no(2)
	}
        ACCESS  read-only
        STATUS  mandatory
        DESCRIPTION
      " Signifies whether a transaction will be automatically started for
	invocations made outside a transaction context. See tuxIfAutoTran
	description for discussion of limitations regarding this attribute."
        ::= { tuxIfQueueEntry 6 }

tuxIfQueueLoad OBJECT-TYPE
        SYNTAX  INTEGER (1..32767)
        ACCESS  read-only
        STATUS  mandatory
        DESCRIPTION
      " This tuxIfQueueTable instance imposes the indicated load on the system. 
	Interface loads are used for load balancing purposes, that is, queues 
	with higher enqueued workloads are less likely to be chosen for a new 
	request."
        ::= { tuxIfQueueEntry 7 }

tuxIfQueuePrio OBJECT-TYPE
        SYNTAX  INTEGER (1..101)
        ACCESS  read-only
        STATUS  mandatory
        DESCRIPTION
      " This tuxIfQueueTable instance has the indicated dequeuing priority. If 
	multiple interface requests are waiting on a queue for servicing, the 
	higher priority requests will be handled first. "
        ::= { tuxIfQueueEntry 8 }

tuxIfQueueTimeout OBJECT-TYPE
        SYNTAX  INTEGER
        ACCESS  read-only
        STATUS  mandatory
        DESCRIPTION
      " Time limit (in seconds) for processing individual method invocations for 
	this interface. Servers processing method invocations for this interface 
	will be abortively terminated if they exceed the specified time limit in 
	processing the request. A value of 0 for this attribute indicates that 
	the server should not be abortively terminated."
        ::= { tuxIfQueueEntry 9 }

tuxIfQueueTranTime OBJECT-TYPE
        SYNTAX  INTEGER
        ACCESS  read-only
        STATUS  mandatory
        DESCRIPTION
      " Transaction timeout value in seconds for transactions automatically 
	started for this tuxIfQueueTable instance. Transactions are started 
	automatically when a requests not in transaction mode is received and 
	the tuxIfAutoTran attribute value for the interface is yes(1). "
        ::= { tuxIfQueueEntry 10 }

tuxIfQueueFbRoutingName OBJECT-TYPE
        SYNTAX  DisplayString (SIZE (1..15))
        ACCESS  read-only
        STATUS  mandatory
        DESCRIPTION
      " The factory based routing criteria associated with this interface."
        ::= { tuxIfQueueEntry 11 }

tuxIfQueueLmid OBJECT-TYPE
        SYNTAX  DisplayString (SIZE (1..30))
        ACCESS  read-only
        STATUS  mandatory
        DESCRIPTION
      " Current Logical machine on which this queue offering this interface is
	located."
        ::= { tuxIfQueueEntry 12 }

tuxIfQueueNumServers OBJECT-TYPE
        SYNTAX  INTEGER
        ACCESS  read-only
        STATUS  mandatory
        DESCRIPTION
      " Number of corresponding servers offering this interface on this queue. " 
        ::= { tuxIfQueueEntry 13 }

tuxIfQueueTpPolicy OBJECT-TYPE
        SYNTAX  INTEGER {
		method(1),
		transaction(2),
		process(3)
	}
        ACCESS  read-only
        STATUS  mandatory
        DESCRIPTION
      " The TP framework deactivation policy. This reflects the policy registered 
	with the framework at server startup. The first server to register the 
	interface sets the value in tuxInterfaceTable. This value cannot be 
	changed. "
        ::= { tuxIfQueueEntry 14 }

tuxIfQueueTxPolicy OBJECT-TYPE
        SYNTAX  INTEGER {
		always(1),
		never(2),
		optional(3),
		ignore(4)
	}
        ACCESS  read-only
        STATUS  mandatory
        DESCRIPTION
      " The transaction policy for the interface. The setting in this attribute 
	affects the effect of the tuxIfQueueAutoTran object. See tuxIfQueueAutoTran 
	for further explanation. This attribute is always read-only. It is set 
	by the developer when the server is built and registered at server 
	startup. "
        ::= { tuxIfQueueEntry 15 }

--******************************************************************************
-- tuxLclIfQueueTable
-- The tuxLclIfQueueTable group represents local attributes of tuxIfQueueTable.
-- These values are specific to the host on which the agent connection is running.
--******************************************************************************
 
tuxLclIfQueueTable OBJECT-TYPE
        SYNTAX  SEQUENCE OF tuxLclIfQueueEntry
        ACCESS  not-accessible
        STATUS  mandatory
        DESCRIPTION
      " The tuxLclIfQueueTable group represents local attributes of tuxIfQueueTable.
   	These values are specific to the host on which the agent connection is 
	running."
        ::= { tuxInterfaceInfo 4 }
 
tuxLclIfQueueEntry OBJECT-TYPE
        SYNTAX tuxLclIfQueueEntry
        ACCESS  not-accessible
        STATUS  mandatory
        DESCRIPTION
        " A row in tuxLclIfQueueTable."
        INDEX { tuxLclIfQueueSerNo }
        ::= { tuxLclIfQueueTable 1 }
 
tuxLclIfQueueEntry ::= SEQUENCE {
   tuxLclIfQueueSerNo
        INTEGER,
   tuxLclIfQueueName
	DisplayString,
   tuxLclIfQueueSrvGrp
	DisplayString,
   tuxLclIfQueueRqAddr
	DisplayString,
   tuxLclIfQueueNcompleted
	INTEGER,
   tuxLclIfQueueNqueued
	INTEGER,
   tuxLclIfQueueCurObjs
	INTEGER,
   tuxLclIfQueueCurTrans
	INTEGER
}

tuxLclIfQueueSerNo OBJECT-TYPE
        SYNTAX  INTEGER
        ACCESS  read-only
        STATUS  mandatory
        DESCRIPTION
      " This object is running number used an index to this table."
        ::= { tuxLclIfQueueEntry 1 }
 
tuxLclIfQueueName OBJECT-TYPE
        SYNTAX  DisplayString (SIZE (1..128))
        ACCESS  read-only
        STATUS  mandatory
        DESCRIPTION
                  " The fully qualified interface name. The interface repository
                    id for the interface. The format of this name is dependent
                    on the options specified in the IDL which generates the
                    interface implementation. See CORBA 2.1 Specification
                    Section 7.6 [CORBA] for details. "
        ::= { tuxLclIfQueueEntry 2 }
 
tuxLclIfQueueSrvGrp OBJECT-TYPE
        SYNTAX  DisplayString (SIZE (1..30))
        ACCESS  read-only
        STATUS  mandatory
        DESCRIPTION
      " Server group name. Server group names cannot contain an asterisk, comma
        or colon. "
        ::= { tuxLclIfQueueEntry 3 }
 
tuxLclIfQueueRqAddr OBJECT-TYPE
        SYNTAX  DisplayString (SIZE (1..30))
        ACCESS  read-only
        STATUS  mandatory
        DESCRIPTION
      " Symbolic address of the request queue for an active server offering this
        interface. See tuxTsrvrRqAddr for more information on this attribute."
        ::= { tuxLclIfQueueEntry 4 }

tuxLclIfQueueNcompleted OBJECT-TYPE
        SYNTAX  INTEGER
        ACCESS  read-only
        STATUS  mandatory
        DESCRIPTION
      " Number of interface method invocations completed since the interface 
	was initially offered.
        Limitation: This attribute is returned only when tuxTdomainLoadBalance is 
	equal to yes(1)."
        ::= { tuxLclIfQueueEntry 5 }

tuxLclIfQueueNqueued OBJECT-TYPE
        SYNTAX  INTEGER
        ACCESS  read-only
        STATUS  mandatory
        DESCRIPTION
      " The number of requests currently enqueued for this interface.
        Limitation: This attribute is returned only when tuxTdomainLoadBalance is 
	equal to yes(1)."
        ::= { tuxLclIfQueueEntry 6 }

tuxLclIfQueueCurObjs OBJECT-TYPE
        SYNTAX  INTEGER
        ACCESS  read-only
        STATUS  mandatory
        DESCRIPTION
      " Number of active objects for this interface for associated queue. This 
	number represents the number of entries in the active object table for 
	this queue on the associated machine. This includes objects that are not 
	in memory but that were invoked within an active transaction. "
        ::= { tuxLclIfQueueEntry 7 }

tuxLclIfQueueCurTrans OBJECT-TYPE
        SYNTAX  INTEGER
        ACCESS  read-only
        STATUS  mandatory
        DESCRIPTION
      " Number of active global transactions associated with this interface for 
	its associated queue. "
        ::= { tuxLclIfQueueEntry 8 }


beaEventFilters OBJECT IDENTIFIER ::= { tuxedo 14 }
 
beaEvtFilterTblStatus OBJECT-TYPE
        SYNTAX  INTEGER {
                sync(1),
                dirty(2)
        }
	ACCESS read-write
        STATUS mandatory
        DESCRIPTION
      " When the agent starts, this objects value is always sync(1). If any
        change is done to beaEvtFilterTable through SET requests, the value
        of this object becomes dirty(2) and the changes in beaEvtFilterTable
        are not applied.
        When the user sets beaEvtFilterTblStatus to sync(1), all changes since
        the last synchronization are applied to the event processing module."
        ::= { beaEventFilters 1 }
 
beaEvtFilterTable OBJECT-TYPE
        SYNTAX SEQUENCE OF BeaEvtFilterEntry
        ACCESS not-accessible
        STATUS mandatory
        DESCRIPTION
      " This MIB group represents all event filters defined for the Agent
        Connection. These are used to determine the set of events to forward as
        SNMP traps.
        NOTE: Changes to this MIB are applied when beaEvtFilterTblStatus is SET
        to sync(1). See description of beaEvtFilterTblStatus for details."
        ::= { beaEventFilters 2 }
 
beaEvtFilterEntry OBJECT-TYPE
        SYNTAX BeaEvtFilterEntry
        ACCESS not-accessible
        STATUS mandatory
        DESCRIPTION
      " This MIB group represents all event filters defined for the Agent
        Connection. These are used to determine the set of events to forward as
        SNMP traps.
        NOTE: 
	1. Changes to this MIB are applied when beaEvtFilterTblStatus is SET
           to sync(1). See description of beaEvtFilterTblStatus for details.
	2. Row Creation: A SET request for a non existing (new FilterId) inst-
	   ance of all objects except beaEvtAgentName is required."
        INDEX   { beaEvtFilterId }
        ::= { beaEvtFilterTable 1 }
 
BeaEvtFilterEntry ::= SEQUENCE {
        beaEvtFilterId
                DisplayString,
        beaEvtAgentName
                DisplayString,
        beaEvtExpr
                DisplayString,
        beaEvtFilter
                DisplayString,
        beaEvtFilterState
                INTEGER
        }

beaEvtFilterId OBJECT-TYPE
        SYNTAX DisplayString (SIZE(1..16))
        ACCESS read-write
        STATUS mandatory
        DESCRIPTION
      " A unique id for the event filter accross the whole filter table.
        NOTE: This object can be SET only during row creation."
        ::= { beaEvtFilterEntry 1 }
 
beaEvtAgentName OBJECT-TYPE
        SYNTAX DisplayString (SIZE(1..32))
        ACCESS read-only
        STATUS mandatory
        DESCRIPTION
      " This object represents the logical agent name of the agent supporting
        this filter. This is for readability purposes only, since the MIB
        returns the event filters only for the agent which was queried."
        ::= { beaEvtFilterEntry 2 }
 
beaEvtExpr OBJECT-TYPE
        SYNTAX DisplayString (SIZE(1..255))
        ACCESS read-write
        STATUS mandatory
        DESCRIPTION
      " Event name expression. The format of this expression is as per the
        recomp(3) TUXEDO man page. This regular expression should match with the
        name of any TUXEDO system event for it to be forwarded as an SNMP trap
        by Agent Connection. For a list of event names see EVENTS(5) man page
        in TUXEDO.
        The default value for this object is all system events - '\.Sys.*'.
        A value of none blocks all events to be forwarded from this agent and
        overrides any other filter entries for the current agent.
        Example:
        '\.Sys.*' will match all system events.
        '\.SysServer.*' will match all system events related to servers. "
        ::= { beaEvtFilterEntry 3 }

beaEvtFilter OBJECT-TYPE
        SYNTAX DisplayString (SIZE(1..255))
        ACCESS read-write
        STATUS mandatory
        DESCRIPTION
      " Event filter expression. Each TUXEDO system event is accompanied with 
  	an FML buffer containing pertinent information about the event. For a
	list of FML fields contained in TUXEDO system Events please refer to 
	EVENTS(5) in the TUXEDO reference manual.
	This filter, if present, is evaluated with respect to the event's 
	buffer contents. It must evaluate to TRUE or that event is not 
	forwarded.
	For details on format of this field please refer to 'Boolean Expres-
	-sions of Fielded Buffers' section in TUXEDO FML Programmer's Guide.
        Example:
	-------
        TA_EVENT_SEVERITY=='ERROR'||TA_EVENT_SEVERITY=='WARN'
        TA_EVENT_SEVERITY!='INFO'
        TA_EVENT_LMID=='SITE1'
       "
        ::= { beaEvtFilterEntry 4 }
 
beaEvtFilterState OBJECT-TYPE
        SYNTAX INTEGER {
                active(1),
                inactive(2),
                invalid(3)
        }
        ACCESS read-write
        STATUS mandatory
        DESCRIPTION
      " This object denotes the current state of the event filter instance.
        GET requests:
        active(1):      This filter is being used.
        inactive(2):    This filter is not being used.
 
        SET requests:
        active(1):      Activate event filter. This can be done only when the
                        filter is in inactive(2) state.
 
        inactive(2):    Inactivate event filter. This can be done only when the
                        filter is in active(1) state.
 
        invalid(3):     Inactivate (if active) and remove event filter. "
        ::= { beaEvtFilterEntry 5 }

-- Added : BEGIN-JANUS-NS-TUXEDO7.1-041400

tuxDmAcl OBJECT IDENTIFIER ::= { tuxedo 80 }
tuxDmConnection OBJECT IDENTIFIER ::= { tuxedo 90 }
tuxDmExport OBJECT IDENTIFIER ::= { tuxedo 100 }
tuxDmImport OBJECT IDENTIFIER ::= { tuxedo 110 }
tuxDmLocal OBJECT IDENTIFIER ::= { tuxedo 120 }
tuxDmOsitp OBJECT IDENTIFIER ::= { tuxedo 130 }
tuxDmPassword OBJECT IDENTIFIER ::= { tuxedo 140 }
tuxDmPrincipalMap OBJECT IDENTIFIER ::= { tuxedo 150 }
tuxDmRemote OBJECT IDENTIFIER ::= { tuxedo 160 }
tuxDmResources OBJECT IDENTIFIER ::= { tuxedo 170 }
tuxDmRouting OBJECT IDENTIFIER ::= { tuxedo 180 }
tuxDmrPrincipal OBJECT IDENTIFIER ::= { tuxedo 190 }
tuxDmSnaCRM OBJECT IDENTIFIER ::= { tuxedo 200 }
tuxDmSnaLink OBJECT IDENTIFIER ::= { tuxedo 210 }
tuxDmSnaStack OBJECT IDENTIFIER ::= { tuxedo 220 }
-- tuxDmStatistics OBJECT IDENTIFIER ::= { tuxedo 230 }
tuxDmTdomain OBJECT IDENTIFIER ::= { tuxedo 240 }
tuxDmTopend OBJECT IDENTIFIER ::= { tuxedo 250 }
tuxDmTransaction OBJECT IDENTIFIER ::= { tuxedo 260 }
 
tuxDmAclTable OBJECT-TYPE
        SYNTAX SEQUENCE OF TuxDmAclEntry
        ACCESS not-accessible
        STATUS mandatory
        DESCRIPTION
      "The TMIB group represents access control information for domains."
        ::= { tuxDmAcl 1 }
 
tuxDmAclEntry OBJECT-TYPE
        SYNTAX TuxDmAclEntry
        ACCESS not-accessible
        STATUS mandatory
        DESCRIPTION
      "The TcwMIB group represents access control information for domains."
        INDEX   { tuxDmAclName }
        ::= { tuxDmAclTable 1 }
 
TuxDmAclEntry ::= SEQUENCE {
        tuxDmAclName
                DisplayString,
        tuxDmrAccessPointList
                DisplayString,
        tuxDmAclState
                INTEGER
        }

tuxDmAclName OBJECT-TYPE
        SYNTAX DisplayString (SIZE(1..15))
        ACCESS read-only
        STATUS mandatory
        DESCRIPTION
      " The access control list name."
        ::= { tuxDmAclEntry 10 }
 
tuxDmrAccessPointList OBJECT-TYPE
        SYNTAX DisplayString (SIZE(0..1000))
        ACCESS read-write
        STATUS mandatory
        DESCRIPTION
     "The list of remote domain access points associated with this access
     control list. tuxDmrAccessPointList is a comma-separated list of remote
     access point names (that is, the value of the tuxDmRemoteDmAccessPoint
     attribute of a valid tuxDmRemote object). The list can contain up to 50
     remote access point identifier elements. Setting this attribute to '*'
     means that all the remote domains in the configuration are associated
     with this entry. blank string means no remote access points are associated with
     this entry. The default is - (equivalent of NULL string)."
        ::= { tuxDmAclEntry 20 }
 
tuxDmAclState OBJECT-TYPE
        SYNTAX INTEGER {
                valid(1),
                invalid(2)
        }
        ACCESS read-write
        STATUS mandatory
        DESCRIPTION
     " This object denotes the current state of the tuxDmAcl instance.
     GET requests:
           valid (1):  tuxDmAcl object is defined and inactive. This is the only
                  valid state for this class. ACL groups are never active.

     SET requests: 
           invalid (2) : delete"
        ::= { tuxDmAclEntry 30 }

-- tuxDmConnection Table

tuxDmConnectionTable OBJECT-TYPE
        SYNTAX SEQUENCE OF TuxDmConnectionEntry
        ACCESS not-accessible
        STATUS mandatory
        DESCRIPTION
      " This class represents the status of connections between
	domain access points."
        ::= { tuxDmConnection 1 }
 
tuxDmConnectionEntry OBJECT-TYPE
        SYNTAX TuxDmConnectionEntry
        ACCESS not-accessible
        STATUS mandatory
        DESCRIPTION
      " This class represents the status of connections between
	domain access points."
        INDEX   { tuxDmConDmlAccessPoint, tuxDmConDmrAccessPoint }
        ::= { tuxDmConnectionTable 1 }
 
TuxDmConnectionEntry ::= SEQUENCE {
        tuxDmConDmlAccessPoint
                DisplayString,
        tuxDmConDmrAccessPoint
                DisplayString,
        tuxDmConDmType
                INTEGER,
        tuxDmConState
                INTEGER,
        tuxDmConDmCurEncryptBits
                INTEGER
        }

tuxDmConDmlAccessPoint OBJECT-TYPE
        SYNTAX DisplayString (SIZE(1..24))
        ACCESS read-only
        STATUS mandatory
        DESCRIPTION
     "The name of the local domain access point identifying the connection
     between the domains."
        ::= { tuxDmConnectionEntry 10 }
 
tuxDmConDmrAccessPoint OBJECT-TYPE
        SYNTAX DisplayString (SIZE(1..24))
        ACCESS read-only
        STATUS mandatory
        DESCRIPTION
     "The name of the remote domain access point identifying the connection
     between the domains."
        ::= { tuxDmConnectionEntry 20 }
 
tuxDmConDmType OBJECT-TYPE
        SYNTAX INTEGER {
                tdomain(1),
                topend(2)
        }
        ACCESS read-only
        STATUS mandatory
        DESCRIPTION
     "The type of domain, which can be either tdomain or topend."
        ::= { tuxDmConnectionEntry 30 }

tuxDmConState OBJECT-TYPE
        SYNTAX INTEGER {
                active(1),
                suspended(2),
                initializing(3),
                inactive(4),
		unknown(5)
        }
        ACCESS read-write
        STATUS mandatory
        DESCRIPTION
     " This object denotes the current state of the tuxDmConnection instance.
     GET requests:
           active (1):       The connection is active.
           suspended (2)    The connection is awaiting retry.
           initializing (3):   The connection is initializing.
           inactive (4):   The specified domain access points are disconnected. (returned in case of Tuxedo 7.1 and later only). 
	   unknown (5) :	state cannot be determined.

     SET requests: 
           active (1):   Connect the specified domain access points. If the
                     current state is suspended or inactive, SET:active
                     places the connection into the state initialiazing,
                     otherwise there is no change.
           inactive (4):  Disconnect the specified domain access points and
                     destroy the tuxDmConnection object."
        ::= { tuxDmConnectionEntry 40 }

tuxDmConDmCurEncryptBits OBJECT-TYPE
        SYNTAX INTEGER {
                enc-0-bit(1),
                enc-40-bits(2),
                enc-56-bits(3),
                enc-128-bits(4)
        }
        ACCESS read-only
        STATUS mandatory
        DESCRIPTION
     "Attribute available when tuxDmConDmType=tdomain

     The level of encryption in use on this connection. 'enc-0-bit' means no
     encryption; 'enc-40-bits', 'enc-56-bits', and 'enc-128-bits' specify the encryption length (in
     bits)."
        ::= { tuxDmConnectionEntry 50 }

-- tuxDmExport Table

tuxDmExportTable OBJECT-TYPE
        SYNTAX SEQUENCE OF TuxDmExportEntry
        ACCESS not-accessible
        STATUS mandatory
        DESCRIPTION
      " This class represents local resources that are exported to one or
	more remote domains through a local access point."
        ::= { tuxDmExport 1 }
 
tuxDmExportEntry OBJECT-TYPE
        SYNTAX TuxDmExportEntry
        ACCESS not-accessible
        STATUS mandatory
        DESCRIPTION
      " This class represents local resources that are exported to one or
	more remote domains through a local access point."
        INDEX   { tuxDmExpDmResourceName, tuxDmExpDmlAccessPoint }
        ::= { tuxDmExportTable 1 }
 
TuxDmExportEntry ::= SEQUENCE {
        tuxDmExpDmResourceName
                DisplayString,
        tuxDmExpDmlAccessPoint
                DisplayString,
        tuxDmExpState
                INTEGER,
        tuxDmExpDmAclName
                DisplayString,
        tuxDmExpDmConv
                INTEGER,
        tuxDmExpDmResourceType
                INTEGER,
        tuxDmExpDmRemoteName
                DisplayString,
        tuxDmExpDmInBufType
                DisplayString,
        tuxDmExpDmOutBufType
                DisplayString,
        tuxDmExpDmTopendProduct
                DisplayString,
        tuxDmExpDmTopendFunction
                DisplayString,
        tuxDmExpDmTopendTarget
                DisplayString,
        tuxDmExpDmTopendQualifier
                INTEGER,
        tuxDmExpDmTopendRtqGroup
                DisplayString,
        tuxDmExpDmTopendRtqName
                DisplayString
        }

tuxDmExpDmResourceName OBJECT-TYPE
        SYNTAX DisplayString (SIZE(1..15))
        ACCESS read-only
        STATUS mandatory
        DESCRIPTION
     "The local resource name for entries of resource type service (the
     service name), qspace (the queue space name), and qname (the queue
     name). For a service entry, the value of this attribute corresponds to
     the value of an active tuxTSvcGrp:tuxTsvcName object.
     This resource is exported to other domains with the same name or with
     the alias defined in the tuxDmExpDmRemoteName or tuxDmExpDmTopend* 
	variables."
        ::= { tuxDmExportEntry 10 }
 
tuxDmExpDmlAccessPoint OBJECT-TYPE
        SYNTAX DisplayString (SIZE(1..30))
        ACCESS read-only
        STATUS mandatory
        DESCRIPTION
     "The local access point name. Setting this attribute to '*' means the
     resource is available at all local access points."
        ::= { tuxDmExportEntry 20 }
 
tuxDmExpState OBJECT-TYPE
        SYNTAX INTEGER {
                valid(1),
                invalid(2)
        }
        ACCESS read-write
        STATUS mandatory
        DESCRIPTION
     " This object denotes the current state of the tuxDmExport instance.
     GET requests:
           valid (1):       The object exists

     SET requests: 
           invalid (2):   delete object "
        ::= { tuxDmExportEntry 30 }

tuxDmExpDmAclName OBJECT-TYPE
        SYNTAX DisplayString (SIZE(1..15))
        ACCESS read-write
        STATUS mandatory
        DESCRIPTION
     "The name of a tuxDmAcl object to use for security on this local
     service. When access is permitted from topend remote access points,
     this optional attribute may be specified if tuxDmExpDmResourceType=service
     and qspace. This attribute is not permitted if tuxDmExpDmResourceType=qname."
        ::= { tuxDmExportEntry 40 }
 
tuxDmExpDmConv OBJECT-TYPE
        SYNTAX INTEGER {
                yes(1),
                no(2)
        }
        ACCESS read-only
        STATUS mandatory
        DESCRIPTION
     "Specifies whether this local service is conversational or not. When
     access is permitted from topend remote access points, this attribute
     must be set to 'N' for entries of tuxDmExpDmResourceType=qspace and qname."
        ::= { tuxDmExportEntry 50 }

tuxDmExpDmResourceType OBJECT-TYPE
        SYNTAX INTEGER {
                service(1),
                qspace(2),
                qname(3)
        }
        ACCESS read-only
        STATUS mandatory
        DESCRIPTION
     "Specifies whether this entry is for a service, qspace or qname. The
     default is service."
        ::= { tuxDmExportEntry 60 }

tuxDmExpDmRemoteName OBJECT-TYPE
        SYNTAX DisplayString (SIZE(1..30))
        ACCESS read-write
        STATUS mandatory
        DESCRIPTION
     "For entries of type service or qspace, this attribute specifies the
     name exported through non-topend remote access points."
        ::= { tuxDmExportEntry 70 }
 
tuxDmExpDmInBufType OBJECT-TYPE
        SYNTAX DisplayString (SIZE(0..513))
        ACCESS read-write
        STATUS mandatory
        DESCRIPTION
     "Attributes available from remote access points of
	tuxDmExpDmResourceType=snax|ositp|topend:

     type[:subtype]-Input buffer type, optionally followed by subtype. If
     this attribute is present, it defines the buffer type [and subtype]
     accepted. This attribute should be defined for entries of
     tuxDmExpDmResourceType=service when access is permitted from remote access
     points using ositp with the UDT application context, or when using
     snax. When access is permitted from topend remote access points, this
     optional attribute may be specified if tuxDmExpDmResourceType=service and
     qname. This attribute is not permitted if tuxDmExpDmResourceType=qspace.

     For BEA TOP END service and queue name entries, the valid values for"
        ::= { tuxDmExportEntry 80 }
 
tuxDmExpDmOutBufType OBJECT-TYPE
        SYNTAX DisplayString (SIZE(0..513))
        ACCESS read-write
        STATUS mandatory
        DESCRIPTION
     "Attributes available from remote access points of
	tuxDmExpDmResourceType=snax|ositp|topend:

     type[:subtype]- Output buffer type, optionally followed by subtype. If
     this attribute is present, it defines the buffer type [and subtype]
     output by the service. This attribute should be defined for entries of
     tuxDmExpDmResourceType=service when access is permitted from remote access
     points using ositp with the UDT application context, or when using
     snax. When access is permitted from topend remote access points, this
     optional attribute may be specified if tuxDmExpDmResourceType=service. This
     attribute is not permitted if tuxDmExpDmResourceType=qspace and qname.

     For BEA TOP END service and queue name entries, the valid values for
     type are: FML32, CARRAY, and X_OCTET."
        ::= { tuxDmExportEntry 90 }
 
tuxDmExpDmTopendProduct OBJECT-TYPE
        SYNTAX DisplayString (SIZE(1..32))
        ACCESS read-write
        STATUS mandatory
        DESCRIPTION
    "Attributes available from remote access points of tuxDmRemoteDmType=topend:

     The BEA TOP END product name. When access is permitted from topend
     remote access points, this attribute must be specified if
     tuxDmExpDmResourceType=service. This attribute is not permitted if
     tuxDmExpDmResourceType=qspace or qname."
        ::= { tuxDmExportEntry 100 }
 
tuxDmExpDmTopendFunction OBJECT-TYPE
        SYNTAX DisplayString (SIZE(1..8))
        ACCESS read-write
        STATUS mandatory
        DESCRIPTION
    "Attributes available from remote access points of tuxDmRemoteDmType=topend:
     The BEA TOP END function name. When access is permitted from topend
     remote access points, this attribute must be specified if
     tuxDmExpDmResourceType=service or qname. This attribute is not permitted if
     tuxDmExpDmResourceType=qspace."
        ::= { tuxDmExportEntry 110 }
 
tuxDmExpDmTopendTarget OBJECT-TYPE
        SYNTAX DisplayString (SIZE(1..8))
        ACCESS read-write
        STATUS mandatory
        DESCRIPTION
    "Attributes available from remote access points of tuxDmRemoteDmType=topend:
     The BEA TOP END Message Sensitive Routing (MSR) target. This attribute
     is optional for entries of tuxDmExpDmResourceType=service, qspace, and qname
     when access is permitted from topend remote access points."
        ::= { tuxDmExportEntry 120 }
 
tuxDmExpDmTopendQualifier OBJECT-TYPE
        SYNTAX INTEGER 
        ACCESS read-write
        STATUS mandatory
        DESCRIPTION
    "Attributes available from remote access points of tuxDmRemoteDmType=topend:
     The BEA TOP END function qualifier. This attribute is optional for
     entries of tuxDmExpDmResourceType=service or qname when access is permitted
     from topend remote access points. This attribute is not permitted if
     tuxDmExpDmResourceType=qspace."
        ::= { tuxDmExportEntry 130 }
 
tuxDmExpDmTopendRtqGroup OBJECT-TYPE
        SYNTAX DisplayString (SIZE(1..32))
        ACCESS read-write
        STATUS mandatory
        DESCRIPTION
    "Attributes available from remote access points of tuxDmRemoteDmType=topend:
     The BEA TOP END Recoverable Transaction Queuing (RTQ) queue group name.
     This attribute must be specified for tuxDmExpDmResourceType=qspace when
     access is permitted from topend remote access points.This attribute is
     not permitted if tuxDmExpDmResourceType=service or qname."
        ::= { tuxDmExportEntry 140 }
 
tuxDmExpDmTopendRtqName OBJECT-TYPE
        SYNTAX DisplayString (SIZE(1..8))
        ACCESS read-write
        STATUS mandatory
        DESCRIPTION
    "Attributes available from remote access points of tuxDmRemoteDmType=topend:
     The BEA TOP END RTQ queue name. This attribute must be specified for
     tuxDmExpDmResourceType=qspace and access is permitted from topend remote
     access points. This attribute is not permitted if
     tuxDmExpDmResourceType=service or qname."
        ::= { tuxDmExportEntry 150 }
 
-- tuxDmImport Table

tuxDmImportTable OBJECT-TYPE
        SYNTAX SEQUENCE OF TuxDmImportEntry
        ACCESS not-accessible
        STATUS mandatory
        DESCRIPTION
	"This group represents remote resources that are imported through
	one or more remote domain access points and made available to the local
	domain through one or more local domain access points."
        ::= { tuxDmImport 1 }
 
tuxDmImportEntry OBJECT-TYPE
        SYNTAX TuxDmImportEntry
        ACCESS not-accessible
        STATUS mandatory
        DESCRIPTION
	"This group represents remote resources that are imported through
	one or more remote domain access points and made available to the local
	domain through one or more local domain access points."
        INDEX   { tuxDmImpDmResourceName,  tuxDmImpDmrAccessPointList,  tuxDmImpDmlAccessPoint }
        ::= { tuxDmImportTable 1 }
 
TuxDmImportEntry ::= SEQUENCE {
        tuxDmImpDmResourceName
                DisplayString,
        tuxDmImpDmrAccessPointList
                DisplayString,
        tuxDmImpDmlAccessPoint
                DisplayString,
        tuxDmImpState
                INTEGER,
        tuxDmImpDmAutoTran
                INTEGER,
        tuxDmImpDmConv
                INTEGER,
        tuxDmImpDmLoad
                INTEGER,
        tuxDmImpDmPrio
                INTEGER,
        tuxDmImpDmResourceType
                INTEGER,
        tuxDmImpDmRemoteName
                DisplayString,
        tuxDmImpDmRoutingName
                DisplayString,
        tuxDmImpDmTranTime
                INTEGER,
        tuxDmImpDmInBufType
                DisplayString,
        tuxDmImpDmOutBufType
                DisplayString,
        tuxDmImpDmteProduct
                DisplayString,
        tuxDmImpDmteFunction
                DisplayString,
        tuxDmImpDmteTarget
                DisplayString,
        tuxDmImpDmteQualifier
                INTEGER,
        tuxDmImpDmteRtqGroup
                DisplayString,
        tuxDmImpDmteRtqName
                DisplayString
        }

tuxDmImpDmResourceName OBJECT-TYPE
        SYNTAX DisplayString (SIZE(1..15))
        ACCESS read-only
        STATUS mandatory
        DESCRIPTION
     "The remote resource name used for entries of resource type service (the
     service name), qspace (the queue space name), and qname (the queue
     name). This resource is imported from remote domains with the same name
     or with the alias defined in the tuxDmImpDmRemoteName or tuxDmImpDmte* 
	variables."
        ::= { tuxDmImportEntry 10 }
 
tuxDmImpDmrAccessPointList OBJECT-TYPE
        SYNTAX DisplayString (SIZE(1..15))
        ACCESS read-only
        STATUS mandatory
        DESCRIPTION
     "Identifies the remote domain access point through which this resource
     should be imported. It is a comma-separated failover
     domain list; it can contain up to three remote domain access points. If
     this attribute is set to '*', the resource can be imported from all
     remote access points."
        ::= { tuxDmImportEntry 20 }
 
tuxDmImpDmlAccessPoint OBJECT-TYPE
        SYNTAX DisplayString (SIZE(1..15))
        ACCESS read-only
        STATUS mandatory
        DESCRIPTION
     "The name of the local domain access point through which this imported
     resource should be made available. If set to the null string, the
     resource is made available through all local domain access points."
        ::= { tuxDmImportEntry 30 }
 
tuxDmImpState OBJECT-TYPE
        SYNTAX INTEGER {
                valid(1),
                invalid(2)
        }
        ACCESS read-write
        STATUS mandatory
        DESCRIPTION
     " This object denotes the current state of the tuxDmImport instance.
     GET requests: 
           valid      The object exists.

     SET requests: 

           invalid    The object is deleted. A state change is
                      allowed in the state active or suspended and results
                      in the state invalid."
        ::= { tuxDmImportEntry 40 }

tuxDmImpDmAutoTran OBJECT-TYPE
        SYNTAX INTEGER {
                yes(1),
                no(2)
        }
        ACCESS read-write
        STATUS mandatory
        DESCRIPTION
     "When a request is received for a resource that is not already within a
     transaction, this attribute automatically starts a transaction for this
     resource."
        ::= { tuxDmImportEntry 50 }

tuxDmImpDmConv OBJECT-TYPE
        SYNTAX INTEGER {
                yes(1),
                no(2)
        }
        ACCESS read-write
        STATUS mandatory
        DESCRIPTION
     "A boolean value (yes Or no) specifying whether the service is
     conversational. When access is permitted from topend remote access
     points, this attribute must be set to no for entries of
     tuxDmImpDmResourceType=qspace and qname."
        ::= { tuxDmImportEntry 60 }

tuxDmImpDmLoad OBJECT-TYPE
        SYNTAX INTEGER (1..32767)
        ACCESS read-write
        STATUS mandatory
        DESCRIPTION
     "The service load."
        ::= { tuxDmImportEntry 70 }

tuxDmImpDmPrio OBJECT-TYPE
        SYNTAX INTEGER (1..100)
        ACCESS read-write
        STATUS mandatory
        DESCRIPTION
     "The dequeuing priority. Service requests with a higher priority are
     serviced first."
        ::= { tuxDmImportEntry 80 }

tuxDmImpDmResourceType OBJECT-TYPE
        SYNTAX INTEGER {
                service(1),
                qspace(2),
                qname(3)
        }
        ACCESS read-write
        STATUS mandatory
        DESCRIPTION
     "Specifies whether this entry is for a service, qspace, or qname. The
     default is service."
        ::= { tuxDmImportEntry 90 }

tuxDmImpDmRemoteName OBJECT-TYPE
        SYNTAX DisplayString (SIZE(1..30))
        ACCESS read-write
        STATUS mandatory
        DESCRIPTION
     "For entries of type service or qspace, this attribute specifies the
     name imported through non-topend remote access points."
        ::= { tuxDmImportEntry 100 }
 
tuxDmImpDmRoutingName OBJECT-TYPE
        SYNTAX DisplayString (SIZE(1..15))
        ACCESS read-write
        STATUS mandatory
        DESCRIPTION
     "The name of a tuxDmRoutingTable object to use for routing criteria for this
     service or qspace."
        ::= { tuxDmImportEntry 110 }
 
tuxDmImpDmTranTime OBJECT-TYPE
        SYNTAX INTEGER (0..32767)
        ACCESS read-write
        STATUS mandatory
        DESCRIPTION
     "Transaction time value, in seconds, for transactions automatically
     started for this service or qspace. Transactions are started
     automatically when a request not in transaction mode is received and
     the tuxDmImpDmAutoTran attribute is set to Y.

     Limitation: Runtime updates to this attribute are not reflected in
     active requests."
        ::= { tuxDmImportEntry 120 }
 
tuxDmImpDmInBufType OBJECT-TYPE
        SYNTAX DisplayString (SIZE(0..256))
        ACCESS read-write
        STATUS mandatory
        DESCRIPTION
     "Attributes available from remote access points of
	tuxDmRemoteDmType=snax|ositp|topend:
     type[:subtype]- Input buffer type, optionally followed by subtype. If
     this attribute is present, it defines the buffer type [and subtype]
     accepted. This attribute should be defined for entries of
     DMRESOURCETYPE=service when access is permitted to remote access points
     using ositp with the UDT application context, or when using snax. When
     access is permitted from topend remote access points, this optional
     attribute may be specified if tuxDmImpDmResourceType=service and qname. This
     attribute is not permitted if tuxDmImpDmResourceType=qspace.

     For BEA TOP END service and queue name entries, the valid values for
     type are: FML32, CARRAY, and X_OCTET."
        ::= { tuxDmImportEntry 130 }
 
tuxDmImpDmOutBufType OBJECT-TYPE
        SYNTAX DisplayString (SIZE(0..256))
        ACCESS read-write
        STATUS mandatory
        DESCRIPTION
     "Attributes available from remote access points of
	tuxDmRemoteDmType=snax|ositp|topend:

     type[:subtype]- Input buffer type, optionally followed by subtype. If
     this attribute is present, it defines the buffer type [and subtype]
     accepted. This attribute should be defined for entries of
     DMRESOURCETYPE=service when access is permitted to remote access points
     using ositp with the UDT application context, or when using snax. When
     access is permitted from topend remote access points, this optional
     attribute may be specified if tuxDmImpDmResourceType=service and qname. This
     attribute is not permitted if tuxDmImpDmResourceType=qspace.

     For BEA TOP END service and queue name entries, the valid values for
     type are: FML32, CARRAY, and X_OCTET."

        ::= { tuxDmImportEntry 140 }
 
tuxDmImpDmteProduct OBJECT-TYPE
        SYNTAX DisplayString (SIZE(1..32))
        ACCESS read-write
        STATUS mandatory
        DESCRIPTION
    "Attributes available from remote access points of tuxDmRemoteDmType=topend:

     The BEA TOP END product name. This attribute must be specified if
     tuxDmImpDmResourceType=service or qname. It is not permitted if
     tuxDmImpDmResourceType=qspace."
        ::= { tuxDmImportEntry 150 }
 
tuxDmImpDmteFunction OBJECT-TYPE
        SYNTAX DisplayString (SIZE(1..8))
        ACCESS read-write
        STATUS mandatory
        DESCRIPTION
    "Attributes available from remote access points of tuxDmRemoteDmType=topend:
     The BEA TOP END function name. This attribute must be specified if
     tuxDmImpDmResourceType=service or qname. It is not permitted if
     tuxDmImpDmResourceType=qspace."
        ::= { tuxDmImportEntry 160 }
 
tuxDmImpDmteTarget OBJECT-TYPE
        SYNTAX DisplayString (SIZE(1..8))
        ACCESS read-write
        STATUS mandatory
        DESCRIPTION
    "Attributes available from remote access points of tuxDmRemoteDmType=topend:
     The BEA TOP END Message Sensitive Routing (MSR) target. This attribute
     is optional attribute for entries of tuxDmImpDmResourceType = service,
     qspace, and qname."
        ::= { tuxDmImportEntry 170 }
 
tuxDmImpDmteQualifier OBJECT-TYPE
        SYNTAX INTEGER 
        ACCESS read-write
        STATUS mandatory
        DESCRIPTION
    "Attributes available from remote access points of tuxDmRemoteDmType=topend:
     The BEA TOP END function qualifier. This attribute is optional for
     entries of tuxDmImpDmResourceType=service and qname. It is not permitted for
     entries of tuxDmImpDmResourceType=qspace."
        ::= { tuxDmImportEntry 180 }
 
tuxDmImpDmteRtqGroup OBJECT-TYPE
        SYNTAX DisplayString (SIZE(1..32))
        ACCESS read-write
        STATUS mandatory
        DESCRIPTION
    "Attributes available from remote access points of tuxDmRemoteDmType=topend:
     The BEA TOP END Recoverable Transaction Queuing (RTQ) queue group name.
     This attribute must be specified if tuxDmImpDmResourceType=qspace. It is not
     permitted if tuxDmImpDmResourceType=service and qname."
        ::= { tuxDmImportEntry 190 }
 
tuxDmImpDmteRtqName OBJECT-TYPE
        SYNTAX DisplayString (SIZE(1..8))
        ACCESS read-write
        STATUS mandatory
        DESCRIPTION
    "Attributes available from remote access points of tuxDmRemoteDmType=topend:
     The BEA TOP END RTQ queue name. This attribute must be specified if
     tuxDmImpDmResourceType=qspace. It is not permitted if
     tuxDmImpDmResourceType=service and qname."
        ::= { tuxDmImportEntry 200 }
 
-- tuxDmLocal Table

tuxDmLocalTable OBJECT-TYPE
        SYNTAX SEQUENCE OF TuxDmLocalEntry
        ACCESS not-accessible
        STATUS mandatory
        DESCRIPTION
	"This group defines a local domain access point. A local domain
	access point is used to control access to local services exported to remote
	domains and to control access to remote services imported from remote
	domains."
        ::= { tuxDmLocal 1 }
 
tuxDmLocalEntry OBJECT-TYPE
        SYNTAX TuxDmLocalEntry
        ACCESS not-accessible
        STATUS mandatory
        DESCRIPTION
	"This group  defines a local domain access point. A local domain
	access point is used to control access to local services exported to remote
	domains and to control access to remote services imported from remote
	domains."
        INDEX   { tuxDmLclDmAccessPoint }
        ::= { tuxDmLocalTable 1 }
 
TuxDmLocalEntry ::= SEQUENCE {
        tuxDmLclDmAccessPoint
                DisplayString,
        tuxDmLclDmAccessPointId
                DisplayString,
        tuxDmLclDmSrvGroup
                DisplayString,
        tuxDmLclDmType
                INTEGER,
        tuxDmLclState
                INTEGER,
        tuxDmLclDmAuditLog
                DisplayString,
        tuxDmLclDmBlockTime
                INTEGER,
        tuxDmLclDmMaxRapTran
                INTEGER,
        tuxDmLclDmMaxTran
                INTEGER,
        tuxDmLclDmSecurity
                INTEGER,
        tuxDmLclDmTlogDev
                DisplayString,
        tuxDmLclDmTlogName
                DisplayString,
        tuxDmLclDmTlogSize
                INTEGER,
        tuxDmLclDmConnectionPolicy
                INTEGER,
        tuxDmLclDmRetryInterval
                INTEGER,
        tuxDmLclDmMaxRetry
                INTEGER,
        tuxDmLclDmConnPrincipalName
                DisplayString,
        tuxDmLclDmMachineType
                DisplayString,
        tuxDmLclDmBlobShmSize
                INTEGER
        }

tuxDmLclDmAccessPoint OBJECT-TYPE
        SYNTAX DisplayString (SIZE(1..30))
        ACCESS read-only
        STATUS mandatory
        DESCRIPTION
     "This is an identifier unique within the scope tuxDmLocal and tuxDmRemote 
	entry names in the
     domain configuration."
        ::= { tuxDmLocalEntry 10 }
 
tuxDmLclDmAccessPointId OBJECT-TYPE
        SYNTAX DisplayString (SIZE(1..30))
        ACCESS read-write
        STATUS mandatory
        DESCRIPTION
     "The domain access point identifier. This identifier is unique across
     all local and remote domain access points."
        ::= { tuxDmLocalEntry 20 }
 
tuxDmLclDmSrvGroup OBJECT-TYPE
        SYNTAX DisplayString (SIZE(1..30))
        ACCESS read-write
        STATUS mandatory
        DESCRIPTION
     "The group name in which the administrative servers and gateway
     processes of the local domain reside."
        ::= { tuxDmLocalEntry 30 }
 
tuxDmLclDmType OBJECT-TYPE
        SYNTAX INTEGER {
                tdomain(1),
                ositp(2),
                snax(3),
                topend(4)
        }
        ACCESS read-write
        STATUS mandatory
        DESCRIPTION
     "The type of domain: tdomain for a BEA Tuxedo system domain, ositp for
     an OSI domain, snax for an SNA domain, or topend for a BEA TOP END
     domain. The presence or absence of other attributes depends on the
     value of this attribute."
        ::= { tuxDmLocalEntry 40 }
 
tuxDmLclState OBJECT-TYPE
        SYNTAX INTEGER {
                valid(1),
                invalid(2)
        }
        ACCESS read-write
        STATUS mandatory
        DESCRIPTION
     " This object denotes the current state of the tuxDmLocal instance.
     GET requests: 
           valid      The object exists.

     SET requests: 

           invalid    The object is deleted. "

        ::= { tuxDmLocalEntry 50 }

tuxDmLclDmAuditLog OBJECT-TYPE
        SYNTAX DisplayString (SIZE(1..78))
        ACCESS read-write
        STATUS mandatory
        DESCRIPTION
     "The name of the audit log file for this local domain. Auditing is
     enabled or disabled by setting the corresponding tuxDmStatisticsDmAudit 
	objectof tuxDmStatisticsTablTable group to either ON or OFF."
        ::= { tuxDmLocalEntry 60 }

tuxDmLclDmBlockTime OBJECT-TYPE
        SYNTAX INTEGER (0..32767)
        ACCESS read-write
        STATUS mandatory
        DESCRIPTION
     "Specifies the maximum wait time allowed for a blocking call. The value
     sets a multiplier of the SCANUNIT parameters specified in the tuxTdomain
     group. The value SCANUNIT * tuxDmLclDmBlockTime must be greater than or equal
     to SCANUNIT and less than 32,768 seconds. If this attribute is not
     specified, the default is set to the value of the tuxDmLclDmBlockTime
     attribute specified in the tuxTdomain object. A timeout always implies a
     failure of the affected request. Notice that the timeout specified for
     transactions in the tuxTdomain is always used when the request is issued
     within a transaction."
        ::= { tuxDmLocalEntry 70 }

tuxDmLclDmMaxRapTran OBJECT-TYPE
        SYNTAX INTEGER (0..32767)
        ACCESS read-write
        STATUS mandatory
        DESCRIPTION
     "The maximum number of remote domain access points that can be involved
     in a single transaction."
        ::= { tuxDmLocalEntry 80 }

tuxDmLclDmMaxTran OBJECT-TYPE
        SYNTAX INTEGER (0..32767)
        ACCESS read-write
        STATUS mandatory
        DESCRIPTION
     "The maximum number of simultaneous transactions allowed on this local
     domain access point. This number must be greater than or equal to
     tuxTdomainMaxGTT object in tuxTdomain group."
        ::= { tuxDmLocalEntry 90 }

tuxDmLclDmSecurity OBJECT-TYPE
        SYNTAX INTEGER {
                none(1),
                app-pw(2),
                dm-pw(3),
                dm-user-pw(4),
                te-clear(5),
                te-safe(6),
                te-private(7)
        }
        ACCESS read-write
        STATUS mandatory
        DESCRIPTION
     "The type of security enabled on this domain. This attribute must be set
     to one of the following.

     none:

          No security is enabled.

     app-pw:

          Valid only when tuxDmRemoteDmType=tdomain. Application password-based
          security is enabled.

     dm-pw:

          Valid only when tuxDmRemoteDmType=tdomain. Domain password-based security
          is enabled.

     dm-user-pw:

          Valid only when tuxDmRemoteDmType=snax. Translation of principal names is
          enabled.

     te-clear:

          Valid only when tuxDmRemoteDmType=topend. BEA TOP END security is enabled
          between the local domain and the BEA TOP END system. Network
          messages are sent in plain text.

     te-safe:

          Valid only when tuxDmRemoteDmType=topend. BEA TOP END security is enabled
          between the local domain and the BEA TOP END system. Network
          messages are protected by a checksum.

     te-private:

          Valid only when tuxDmRemoteDmType=topend. BEA TOP END security is enabled
          between the local domain and the BEA TOP END system. Network
          messages are encrypted."
        ::= { tuxDmLocalEntry 100 }

tuxDmLclDmTlogDev OBJECT-TYPE
        SYNTAX DisplayString (SIZE(1..256))
        ACCESS read-write
        STATUS mandatory
        DESCRIPTION
     "The device (raw slice) or file containing the domain TLOG for this
     local domain access point. The TLOG is stored as a BEA Tuxedo System
     VTOC table on the device. For reliability, the use of a device (raw
     slice) is recommended."
        ::= { tuxDmLocalEntry 110 }
 
tuxDmLclDmTlogName OBJECT-TYPE
        SYNTAX DisplayString (SIZE(1..30))
        ACCESS read-write
        STATUS mandatory
        DESCRIPTION
     "The domain TLOG name for this local domain access point. If more than
     one TLOG exists on the same device, each TLOG must have a unique name."
        ::= { tuxDmLocalEntry 120 }
 
tuxDmLclDmTlogSize OBJECT-TYPE
        SYNTAX INTEGER
        ACCESS read-write
        STATUS mandatory
        DESCRIPTION
     "The size in pages of the TLOG for this local domain access point. This
     size is constrained by the amount of space available on the device
     identified in tuxDmLclTlogDev."
        ::= { tuxDmLocalEntry 130 }
 
tuxDmLclDmConnectionPolicy OBJECT-TYPE
        SYNTAX INTEGER {
                on-demand(1),
                on-startup(2),
                incoming-only(3)
        }
        ACCESS read-write
        STATUS mandatory
        DESCRIPTION
	"Attributes available when tuxDmRemoteDmType = tdomain | topend

     Specifies the conditions under which a local domain gateway tries to
     establish a connection to a remote domain. Supported values are:
     on-demand, on-startup, or incoming-only.

     on-demand

          Means that a connection is attempted only when requested by either
          a client request to a remote service or an administrative
          'connect' command. The default setting for this variable
          is on-demand. The on-demand policy provides the
          equivalent behavior to previous releases, in which the
          this variable was not explicitly available.
          Connection retry processing is not allowed with this policy.

     on-startup

          Means that a domain gateway attempts to establish a connection
          with its remote domain access points at gateway server
          initialization time. Remote services (that is, services advertised
          by the domain gateway for this local access point) are advertised
          only if a connection is successfully established to that remote
          domain access point. Therefore, if there is no active connection
          to a remote domain access point, then the remote services are
          suspended. By default, this connection policy retries failed
          connections every 60 seconds; however, you can specify a different
          value for this interval using the tuxDmLclMaxRetry and
          tuxDmLclDmRetryInterval attributes.

     incoming-only

          Means that a domain gateway does not attempt an initial connection
          to remote domain access points upon starting, and remote services
          are initially suspended. The domain gateway is available for
          incoming connections from remote domain access points, and remote
          services are advertised when the domain gateway for this local
          domain access point receives an incoming connection. Connection
          retry processing is not allowed when the connection policy is
          incoming-only."
        ::= { tuxDmLocalEntry 140 }
 
tuxDmLclDmRetryInterval OBJECT-TYPE
        SYNTAX INTEGER 
        ACCESS read-write
        STATUS mandatory
        DESCRIPTION
     "The number of seconds between automatic attempts to establish a
     connection to remote domain access points. The minimum value is 0 and
     the maximum value is 2147483647. The default setting is 60. If
     tuxDmLclDmMaxRetry is set to 0, then setting tuxDmLclDmRetryInterval is not
     allowed.

     This attribute is valid only when the tuxDmLclDmConnectionPolicy attribute
     is set to on-startup. For other connection policies, automatic retries
     are disabled."
        ::= { tuxDmLocalEntry 150 }
 
tuxDmLclDmMaxRetry OBJECT-TYPE
        SYNTAX INTEGER
        ACCESS read-write
        STATUS mandatory
        DESCRIPTION
     "The number of times that a domain gateway tries to establish
     connections to remote domain access points. The minimum value is 0 and
     the maximum is MAXLONG. MAXLONG indicates that retry processing is
     repeated indefinitely, or until a connection is established. For a
     connection policy of on-startup, the default setting for tuxDmLclMaxRetry
     is MAXLONG. Setting this attribute to 0 turns off the auto retry
     mechanism. For other connection policies, auto retries are disabled.

     The tuxDmLclMaxRetry attribute is valid only when the connection policy is
     on-startup."
        ::= { tuxDmLocalEntry 160 }
 
tuxDmLclDmConnPrincipalName OBJECT-TYPE
        SYNTAX DisplayString (SIZE(0..511))
        ACCESS read-write
        STATUS mandatory
        DESCRIPTION
"The connection principal name identifier, which is the principal name used for verifying the identity of this local domain access point when establishing a connection to a remote
     domain access point. This attribute only applies to domains of type TDOMAIN that are running BEA Tuxedo 7.1 or later software.

     This variable may contain a maximum of 511 characters (excluding the terminating null character). If this attribute is not specified, the connection
     principal name defaults to the tuxDmLclDmAccessPointId string for this local domain access point.

     For default authentication plug-ins, if a value is assigned to this variablee for this local domain access point, it must be the same as the value assigned to
     the tuxDmLclDmAccessPointId attribute for this local domain access point. If these values do not match, the local domain gateway process will not boot, and the system will generate the
     following userlog(3c) message: ERROR: Unable to acquire credentials."
        ::= { tuxDmLocalEntry 170 }
 
tuxDmLclDmMachineType OBJECT-TYPE
        SYNTAX DisplayString (SIZE(0..15))
        ACCESS read-write
        STATUS mandatory
        DESCRIPTION
     "Used for grouping domains so that encoding/decoding of messages between

     domains can be bypassed. If it is not specified, the
     default is to turn encoding/decoding on. If the value set for the
     this field is the same in both the DM_LOCAL and the
     DM_REMOTE section of a domain configuration file, data
     encoding/decoding is bypassed. The value set for this variable can
     be any string value up to 15 characters in length. It is used only for
     comparison.

     This attribute is valid only when tuxDmRemoteDmType=tdomain."
        ::= { tuxDmLocalEntry 180 }
 
tuxDmLclDmBlobShmSize OBJECT-TYPE
        SYNTAX INTEGER
        ACCESS read-write
        STATUS mandatory
        DESCRIPTION
     "Relevant only to local domain access point entries. Specifies the
     amount of shared memory allocated to storing binary large object log
     information specific to ositp or topend."
        ::= { tuxDmLocalEntry 190 }
 
-- tuxDmOsitp Table

tuxDmOsitpTable OBJECT-TYPE
        SYNTAX SEQUENCE OF TuxDmOsitpEntry
        ACCESS not-accessible
        STATUS mandatory
        DESCRIPTION
	"This group defines the OSI TP protocol related configuration
	information for a specific local or remote domain access point."
        ::= { tuxDmOsitp 1 }
 
tuxDmOsitpEntry OBJECT-TYPE
        SYNTAX TuxDmOsitpEntry
        ACCESS not-accessible
        STATUS mandatory
        DESCRIPTION
	"This group defines the OSI TP protocol related configuration
	information for a specific local or remote domain access point."
        INDEX   { tuxDmOsiDmAccessPoint }
        ::= { tuxDmOsitpTable 1 }
 
TuxDmOsitpEntry ::= SEQUENCE {
        tuxDmOsiDmAccessPoint
                DisplayString,
        tuxDmOsiState
                INTEGER,
        tuxDmOsiDmApt
                DisplayString,
        tuxDmOsiDmAeq
                DisplayString,
        tuxDmOsiDmNwDevice
                DisplayString,
        tuxDmOsiDmAcn
                INTEGER,
        tuxDmOsiDmApid
                INTEGER,
        tuxDmOsiDmAeid
                INTEGER,
        tuxDmOsiDmUrch
                DisplayString,
        tuxDmOsiDmMaxListeningEp
                INTEGER,
        tuxDmOsiDmXatmiEncoding
                INTEGER
        }

tuxDmOsiDmAccessPoint OBJECT-TYPE
        SYNTAX DisplayString (SIZE(1..30))
        ACCESS read-only
        STATUS mandatory
        DESCRIPTION
     "The domain access point name for which this entry provides the
     protocol-specific configuration information. This field matches the
     domain access point name given in the tuxDmLocal or tuxDmRemote entry
     that defines the protocol independent configuration of the domain
     access point."
        ::= { tuxDmOsitpEntry 10 }
 
tuxDmOsiState OBJECT-TYPE
        SYNTAX INTEGER {
                valid(1),
                invalid(2)
        }
        ACCESS read-write
        STATUS mandatory
        DESCRIPTION
     " This object denotes the current state of the tuxDmOsitp instance.
     GET requests: 
           valid      The object exists.

     SET requests: 

           invalid    The object is deleted. "
        ::= { tuxDmOsitpEntry 20 }

tuxDmOsiDmApt OBJECT-TYPE
        SYNTAX DisplayString (SIZE(1..78))
        ACCESS read-write
        STATUS mandatory
        DESCRIPTION
     "The application process title of the domain access point in object
     identifier form."
        ::= { tuxDmOsitpEntry 30 }

tuxDmOsiDmAeq OBJECT-TYPE
        SYNTAX DisplayString (SIZE(1..78))
        ACCESS read-write
        STATUS mandatory
        DESCRIPTION
     "The application entity qualifier of the domain access point in integer
     form."
        ::= { tuxDmOsitpEntry 40 }

tuxDmOsiDmNwDevice OBJECT-TYPE
        SYNTAX DisplayString (SIZE(1..78))
        ACCESS read-write
        STATUS mandatory
        DESCRIPTION
     "Specifies the network device to be used. This attribute is relevant
     when defining a local domain access point and ignored for a remote
     domain access point."
        ::= { tuxDmOsitpEntry 50 }

tuxDmOsiDmAcn OBJECT-TYPE
        SYNTAX INTEGER {
                xatmi(1),
                udt(2)
        }
        ACCESS read-write
        STATUS mandatory
        DESCRIPTION
     "The application context name to use with this domain access point. When
     establishing a dialogue to a remote domain access point, the
     application context name from the remote domain access point is used,
     if it is present. If the application context name from the remote
     domain access point is absent, the application context name from the
     local domain access point is used. The value xatmi selects the use of
     the X/Open defined xatmi Application Service Element (ASE) and
     encoding. The value udt selects the use of the ISO/IEC 10026-5 User
     Data Transfer encoding."
        ::= { tuxDmOsitpEntry 60 }

tuxDmOsiDmApid OBJECT-TYPE
        SYNTAX INTEGER 
        ACCESS read-write
        STATUS mandatory
        DESCRIPTION
     "This optional attribute defines the application process invocation
     identifier to be used on this domain access point."
        ::= { tuxDmOsitpEntry 70 }

tuxDmOsiDmAeid OBJECT-TYPE
        SYNTAX INTEGER 
        ACCESS read-write
        STATUS mandatory
        DESCRIPTION
	"This optional attribute defines the application entity invocation identifier to be used on this domain access point. "
        ::= { tuxDmOsitpEntry 80 }
 
tuxDmOsiDmUrch OBJECT-TYPE
        SYNTAX DisplayString (SIZE(0..30))
        ACCESS read-write
        STATUS mandatory
        DESCRIPTION
     "Specifies the user portion of the OSI TP recovery context handle. It
     may be required by an OSI TP provider in order to perform recovery of
     distributed transactions after a communications line or system failure.
     This attribute is relevant when defining a local domain access point
     and ignored for a remote domain access point."
        ::= { tuxDmOsitpEntry 90 }
 
tuxDmOsiDmMaxListeningEp OBJECT-TYPE
        SYNTAX INTEGER (1..32767)
        ACCESS read-write
        STATUS mandatory
        DESCRIPTION
     "Specifies the number of endpoints awaiting incoming OSI TP dialogues.
     This attribute is relevant when defining a local domain access point
     and ignored for a remote domain access point."
        ::= { tuxDmOsitpEntry 100 }
 
tuxDmOsiDmXatmiEncoding OBJECT-TYPE
        SYNTAX INTEGER {
                cae(1),
                prelimnary(2),
                oltp-tm2200(3)
        }
        ACCESS read-write
        STATUS mandatory
        DESCRIPTION
     "Specifies the version of the XATMI protocol used to communicate with a
     remote system. Valid values are:

     cae

     preliminary

     oltp-tm2200

          This attribute is relevant for remote domain access points and
          ignored for local domain access points."
        ::= { tuxDmOsitpEntry 110 }
 
-- tuxDmPassword Table

tuxDmPasswordTable OBJECT-TYPE
        SYNTAX SEQUENCE OF TuxDmPasswordEntry
        ACCESS not-accessible
        STATUS mandatory
        DESCRIPTION
	"This group represents configuration information for
	inter-domain authentication through access points of type tdomain."
        ::= { tuxDmPassword 1 }
 
tuxDmPasswordEntry OBJECT-TYPE
        SYNTAX TuxDmPasswordEntry
        ACCESS not-accessible
        STATUS mandatory
        DESCRIPTION
	"This group represents configuration information for
	inter-domain authentication through access points of type tdomain."
        INDEX   { tuxDmPasswdDmlAccessPoint, tuxDmPasswdDmrAccessPoint }
        ::= { tuxDmPasswordTable 1 }
 
TuxDmPasswordEntry ::= SEQUENCE {
        tuxDmPasswdDmlAccessPoint
                DisplayString,
        tuxDmPasswdDmrAccessPoint
                DisplayString,
        tuxDmPasswdDmlPWD
                DisplayString,
        tuxDmPasswdDmrPWD
                DisplayString,
        tuxDmPasswdState
                INTEGER
        }

tuxDmPasswdDmlAccessPoint OBJECT-TYPE
        SYNTAX DisplayString (SIZE(1..24))
        ACCESS read-only
        STATUS mandatory
        DESCRIPTION
     "The name of the local domain access point to which the password
     applies."
        ::= { tuxDmPasswordEntry 10 }
 
tuxDmPasswdDmrAccessPoint OBJECT-TYPE
        SYNTAX DisplayString (SIZE(1..24))
        ACCESS read-only
        STATUS mandatory
        DESCRIPTION
     "The name of the remote domain access point to which the password
     applies."
        ::= { tuxDmPasswordEntry 20 }

tuxDmPasswdDmlPWD OBJECT-TYPE
        SYNTAX DisplayString (SIZE(1..30))
        ACCESS write-only
        STATUS mandatory
        DESCRIPTION
     "The local password to be used to authenticate connections between the
     local domain access point identified by tuxDmPasswdDmlAccessPoint and the
     remote domain access point identified by tuxDmPasswdDmrAccessPoint."
        ::= { tuxDmPasswordEntry 30 }

tuxDmPasswdDmrPWD OBJECT-TYPE
        SYNTAX DisplayString (SIZE(1..30))
        ACCESS write-only
        STATUS mandatory
        DESCRIPTION
     "The remote password to be used to authenticate connections between the
     local domain access point identified by tuxDmPasswdDmlAccessPoint and the
     remote domain access point identified by tuxDmPasswdDmrAccessPoint."
        ::= { tuxDmPasswordEntry 40 }

tuxDmPasswdState OBJECT-TYPE
        SYNTAX INTEGER {
                valid(1),
                invalid(2),
                recrypt(3)
        }
        ACCESS read-write
        STATUS mandatory
        DESCRIPTION
     " This object denotes the current state of the tuxDmPassword instance.
     GET requests: 
           valid      The object exists.

     SET requests: 

           invalid    The object is deleted.
           recrypt    Re-encrypt all passwords using a new encryption key."
        ::= { tuxDmPasswordEntry 50 }

-- tuxDmPrincipalMap Table

tuxDmPrincipalMapTable OBJECT-TYPE
        SYNTAX SEQUENCE OF TuxDmPrincipalMapEntry
        ACCESS not-accessible
        STATUS mandatory
        DESCRIPTION
	"This group represents configuration information for
	mapping principal names to and from external principal names across access
	points of type snax."
        ::= { tuxDmPrincipalMap 1 }
 
tuxDmPrincipalMapEntry OBJECT-TYPE
        SYNTAX TuxDmPrincipalMapEntry
        ACCESS not-accessible
        STATUS mandatory
        DESCRIPTION
	"This group represents configuration information for
	mapping principal names to and from external principal names across access
	points of type snax."
        INDEX   { tuxDmPrinMapDmlAccessPoint, tuxDmPrinMapDmrAccessPoint, tuxDmPrinMapDmPrinName, tuxDmPrinMapDmrPrinName }
        ::= { tuxDmPrincipalMapTable 1 }
 
TuxDmPrincipalMapEntry ::= SEQUENCE {
        tuxDmPrinMapDmlAccessPoint
                DisplayString,
        tuxDmPrinMapDmrAccessPoint
                DisplayString,
        tuxDmPrinMapDmPrinName
                DisplayString,
        tuxDmPrinMapDmrPrinName
                DisplayString,
        tuxDmPrinMapDirection
                INTEGER,
        tuxDmPrinMapState
                INTEGER
        }

tuxDmPrinMapDmlAccessPoint OBJECT-TYPE
        SYNTAX DisplayString (SIZE(1..12))
        ACCESS read-only
        STATUS mandatory
        DESCRIPTION
     "The local domain access point to which the principal mapping applies."
        ::= { tuxDmPrincipalMapEntry 10 }
 
tuxDmPrinMapDmrAccessPoint OBJECT-TYPE
        SYNTAX DisplayString (SIZE(1..12))
        ACCESS read-only
        STATUS mandatory
        DESCRIPTION
     "The remote domain access point to which the principal mapping applies."
        ::= { tuxDmPrincipalMapEntry 20 }

tuxDmPrinMapDmPrinName OBJECT-TYPE
        SYNTAX DisplayString (SIZE(1..12))
        ACCESS read-only
        STATUS mandatory
        DESCRIPTION
     "The local principal name in the principal mapping."
        ::= { tuxDmPrincipalMapEntry 30 }

tuxDmPrinMapDmrPrinName OBJECT-TYPE
        SYNTAX DisplayString (SIZE(1..12))
        ACCESS read-only
        STATUS mandatory
        DESCRIPTION
     "The remote principal name in the principal mapping."
        ::= { tuxDmPrincipalMapEntry 40 }

tuxDmPrinMapDirection OBJECT-TYPE
        SYNTAX INTEGER {
                in(1),
                out(2),
                both(3)
        }
        ACCESS read-write
        STATUS mandatory
        DESCRIPTION
     "The direction to which the principal mapping applies.

     in

          Is incoming to this BEA Tuxedo domain through the given remote
          domain access point and local domain access point.

     out

          Is outgoing from this BEA Tuxedo domain through the given local
          domain access point and remote domain access point.

     both

          Applies to both incoming and outgoing."
        ::= { tuxDmPrincipalMapEntry 50 }

tuxDmPrinMapState OBJECT-TYPE
        SYNTAX INTEGER {
                valid(1),
                invalid(2)
        }
        ACCESS read-write
        STATUS mandatory
        DESCRIPTION
     " This object denotes the current state of the tuxDmPrincipalMap instance.
     GET requests: 
           valid      The object exists.

     SET requests: 

           invalid    The object is deleted."
        ::= { tuxDmPrincipalMapEntry 60 }

-- tuxDmRemote Table

tuxDmRemoteTable OBJECT-TYPE
        SYNTAX SEQUENCE OF TuxDmRemoteEntry
        ACCESS not-accessible
        STATUS mandatory
        DESCRIPTION
	"The tuxDmRemote class represents remote domain access point configuration
	information. Local resources that may be exported through one or more local
	domain access points are made accessible to a remote domain through a remote
	domain access point. Similarly remote resources are imported from a remote
	domain through a remote domain access point."
        ::= { tuxDmRemote 1 }
 
tuxDmRemoteEntry OBJECT-TYPE
        SYNTAX TuxDmRemoteEntry
        ACCESS not-accessible
        STATUS mandatory
        DESCRIPTION
	"The tuxDmRemote class represents remote domain access point configuration
	information. Local resources that may be exported through one or more local
	domain access points are made accessible to a remote domain through a remote
	domain access point. Similarly remote resources are imported from a remote
	domain through a remote domain access point."
        INDEX   { tuxDmRemoteDmAccessPoint }
        ::= { tuxDmRemoteTable 1 }
 
TuxDmRemoteEntry ::= SEQUENCE {
        tuxDmRemoteDmAccessPoint
                DisplayString,
        tuxDmRemoteDmAccessPointID
                DisplayString,
        tuxDmRemoteType
                INTEGER,
        tuxDmRemoteState
                INTEGER,
        tuxDmRemoteDmCodePage
                DisplayString,
        tuxDmRemoteDmAclPolicy
                INTEGER,
        tuxDmRemoteDmConnPrincipalName
                DisplayString,
        tuxDmRemoteDmLocalPrincipalName
                DisplayString,
        tuxDmRemoteDmMachineType
                DisplayString
        }

tuxDmRemoteDmAccessPoint OBJECT-TYPE
        SYNTAX DisplayString (SIZE(1..30))
        ACCESS read-only
        STATUS mandatory
        DESCRIPTION
     "The name of this tuxDmRemote entry. this is an identifier
     unique within the scope of tuxDmLocal and tuxDmRemote entry names in
     the domain configuration."
        ::= { tuxDmRemoteEntry 10 }
 
tuxDmRemoteDmAccessPointID OBJECT-TYPE
        SYNTAX DisplayString (SIZE(1..30))
        ACCESS read-write
        STATUS mandatory
        DESCRIPTION
     "The access point identifier. This identifier is unique across all local
     and remote domain access points."
        ::= { tuxDmRemoteEntry 20 }

tuxDmRemoteType OBJECT-TYPE
        SYNTAX INTEGER {
                tdomain(1),
                ositp(2),
                snax(3),
                topend(4)
        }
        ACCESS read-write
        STATUS mandatory
        DESCRIPTION
     "The type of domain: tdomain for a BEA Tuxedo system domain, ositp for
     an OSI domain, snax for an SNA domain, or topend for a BEA TOP END
     domain. The presence or absence of other attributes depends on the
     value of this attribute."
        ::= { tuxDmRemoteEntry 30 }

tuxDmRemoteState OBJECT-TYPE
        SYNTAX INTEGER {
                valid(1),
                invalid(2)
        }
        ACCESS read-write
        STATUS mandatory
        DESCRIPTION
     " This object denotes the current state of the tuxDmRemote instance.
     GET requests: 
           valid      The object exists.

     SET requests: 

           invalid    The object is deleted."
        ::= { tuxDmRemoteEntry 40 }

tuxDmRemoteDmCodePage OBJECT-TYPE
        SYNTAX DisplayString (SIZE(1..20))
        ACCESS read-write
        STATUS mandatory
        DESCRIPTION
	"Attributes available when tuxDmRemoteDmType=snax
     	The name of the default translation tables to use in translating
     	requests and replies sent through this access point."
        ::= { tuxDmRemoteEntry 50 }

tuxDmRemoteDmAclPolicy OBJECT-TYPE
        SYNTAX INTEGER {
		local (1),
		global (2)
		}
        ACCESS read-write
        STATUS mandatory
        DESCRIPTION
"The access control list (ACL) policy for this remote domain access point. This attribute only applies to domains of type TDOMAIN that are running BEA Tuxedo 7.1 or later software.

     local means that the local domain modifies the identity of service requests received from this remote domain to the principal name specified in the tuxDmRemoteDmLocalPrincipalName variable for this remote domain access point. global means that the local domain passes the service requests with no change. If not specified, the default is local."
        ::= { tuxDmRemoteEntry 60 }

tuxDmRemoteDmConnPrincipalName OBJECT-TYPE
        SYNTAX DisplayString (SIZE(0..511))
        ACCESS read-write
        STATUS mandatory
        DESCRIPTION
"The connection principal name identifier, which is the principal name used for verifying the identity of this remote domain access point when establishing a connection to the local
     domain access point. This attribute only applies to domains of type TDOMAIN that are running BEA Tuxedo 7.1 or later software.

     This variable contain a maximum of 511 characters (excluding the terminating null character). If this attribute is not specified, the connection
     principal name defaults to the tuxDmRemoteAccessPointId string for this remote domain access point.

     For default authentication plug-ins, if a value is assigned to this variable for this remote domain access point, it must be the same as the value assigned
     to the tuxDmRemoteDmAccessPointId attribute for this remote domain access point. If these values do not match, any attempt to set up a connection between the local domain gateway and
     the remote domain gateway "
        ::= { tuxDmRemoteEntry 70 }

tuxDmRemoteDmLocalPrincipalName OBJECT-TYPE
        SYNTAX DisplayString (SIZE(0..511))
        ACCESS read-write
        STATUS mandatory
        DESCRIPTION
"The local principal name identifier, which is the identity assigned by the local domain to service requests received from this remote domain. This attribute only applies to domains of
     type TDOMAIN that are running BEA Tuxedo 7.1 or later software.

     This variable is valid only if the tuxDmRemoteAclPolicy variable for this remote domain is set (or defaulted) to local. This variable may contain a maximum of 511 characters (excluding the terminating null character). If this attribute is not specified, the local principal name defaults to the
     tuxDmRemoteDmAccessPointId string for this remote domain access point."
        ::= { tuxDmRemoteEntry 80 }

tuxDmRemoteDmMachineType OBJECT-TYPE
        SYNTAX DisplayString (SIZE(0..15))
        ACCESS read-write
        STATUS mandatory
        DESCRIPTION
	"Attributes available when tuxDmRemoteDmType=tdomain

     Used for grouping domains so that encoding/decoding of messages between
     domains can be bypassed. If it is not specified, the
     default is to turn encoding/decoding on. If the value set for
     this field is the same in both the DM_LOCAL and the
     DM_REMOTE section of a domain configuration file, data
     encoding/decoding is bypassed. The value set for this variable can
     be any string value up to 15 characters in length. It is used only for
     comparison."
        ::= { tuxDmRemoteEntry 90 }

-- tuxDmResources Table

tuxDmResourcesTable OBJECT-TYPE
        SYNTAX SEQUENCE OF TuxDmResourcesEntry
        ACCESS not-accessible
        STATUS mandatory
        DESCRIPTION
	"This group represents Domains-specific configuration
	information."
        ::= { tuxDmResources 1 }
 
tuxDmResourcesEntry OBJECT-TYPE
        SYNTAX TuxDmResourcesEntry
        ACCESS not-accessible
        STATUS mandatory
        DESCRIPTION
	"This group represents Domains-specific configuration
	information."
        INDEX   { tuxDmResourcesDmVersion }
        ::= { tuxDmResourcesTable 1 }
 
TuxDmResourcesEntry ::= SEQUENCE {
        tuxDmResourcesDmVersion
                DisplayString
        }

tuxDmResourcesDmVersion OBJECT-TYPE
        SYNTAX DisplayString (SIZE(1..30))
        ACCESS read-only
        STATUS mandatory
        DESCRIPTION
     "A user-supplied identifier for the Domains configuration."
        ::= { tuxDmResourcesEntry 10 }
 
-- tuxDmRouting Table

tuxDmRoutingTable OBJECT-TYPE
        SYNTAX SEQUENCE OF TuxDmRoutingEntry
        ACCESS not-accessible
        STATUS mandatory
        DESCRIPTION
	"The tuxDmRoutingTable class represents routing criteria information for routing
	requests to a domain through a remote domain access point."
        ::= { tuxDmRouting 1 }
 
tuxDmRoutingEntry OBJECT-TYPE
        SYNTAX TuxDmRoutingEntry
        ACCESS not-accessible
        STATUS mandatory
        DESCRIPTION
	"The tuxDmRoutingTable class represents routing criteria information for routing
	requests to a domain through a remote domain access point."
        INDEX   { tuxDmRoutingDmRoutingName, tuxDmRoutingDmBufType }
        ::= { tuxDmRoutingTable 1 }
 
TuxDmRoutingEntry ::= SEQUENCE {
        tuxDmRoutingDmRoutingName
                DisplayString,
        tuxDmRoutingDmBufType
                DisplayString,
        tuxDmRoutingDmField
                DisplayString,
        tuxDmRoutingDmFieldType
                INTEGER,
        tuxDmRoutingDmRanges
                DisplayString,
        tuxDmRoutingState
                INTEGER
        }

tuxDmRoutingDmRoutingName OBJECT-TYPE
        SYNTAX DisplayString (SIZE(1..15))
        ACCESS read-only
        STATUS mandatory
        DESCRIPTION
     "The name of the routing criteria table entry."
        ::= { tuxDmRoutingEntry 10 }
 
tuxDmRoutingDmBufType OBJECT-TYPE
        SYNTAX DisplayString (SIZE(1..30))
        ACCESS read-only
        STATUS mandatory
        DESCRIPTION
     "type1[:subtype1[,subtype2 . . . ]][;type2[:subtype3[,subtype4 . . . ]]
     . . . ]

     List of types and subtypes of data buffers for which this routing entry
     is valid. A maximum of 32 type/subtype combinations is allowed. The
     types are restricted to the following: FML, XML, VIEW, X_C_TYPE, or
     X_COMMON. No subtype can be specified for type FML or XML; subtypes are
     required for types VIEW, X_C_TYPE, and X_COMMON ('*' is not allowed).
     Note that subtype names should not contain semicolon, colon, comma, or
     asterisk characters. Duplicate type/subtype pairs cannot be specified
     for the same routing criterion name; more than one routing entry can
     have the same criterion name as long as the type/subtype pairs are
     unique. If multiple buffer types are specified for a single routing
     entry, the data types of the routing field for each buffer type must be
     the same."
        ::= { tuxDmRoutingEntry 20 }

tuxDmRoutingDmField OBJECT-TYPE
        SYNTAX DisplayString (SIZE(1..30))
        ACCESS read-write
        STATUS mandatory
        DESCRIPTION
     "Routing field name. This field is assumed to be an FML buffer, XML
     buffer, or VIEW field name that is identified in an FML field table
     (using the FLDTBLDIR and FIELDTBLS environment variables) or an FML
     VIEW table (using the VIEWDIR and VIEWFILES environment variables),
     respectively. This information is used to get the associated field
     value for data-dependent routing to an access point of a remote domain.

     For an XML buffer type, It contains either a routing element
     type (or name) or a routing element attribute name.

     The syntax of this variable for an XML buffer type is as
     follows.

          root_element[/child_element][/child_element][/. . .][/@attribute_name]

     The element is assumed to be an XML document or datagram element type.
     Indexing is not supported. Therefore, the BEA Tuxedo system recognizes
     only the first occurrence of a given element type when processing an
     XML buffer for data-dependent routing. This information is used to get
     the associated element content for data-dependent routing while sending
     a message. The content must be a string encoded in UTF-8.

     The attribute is assumed to be an XML document or datagram attribute of
     the defined element. This information is used to get the associated
     attribute value for data-dependent routing while sending a message. The
     value must be a string encoded in UTF-8.

     The combination of element name and attribute name may contain up to 30
     characters.

     The type of the routing field can be specified by the tuxDmRoutingFieldType
     attribute."
        ::= { tuxDmRoutingEntry 30 }

tuxDmRoutingDmFieldType OBJECT-TYPE
        SYNTAX INTEGER {
	char (1),
	short (2),
	long (3),
	float (4),
	double (5),
	string (6)
	}
        ACCESS read-write
        STATUS mandatory
        DESCRIPTION
     "The type can be char, short, long, float, double, or string; only one
     type is allowed. This attribute is used only for routing XML buffers.
     The default type of the routing field is string."
        ::= { tuxDmRoutingEntry 40 }

tuxDmRoutingDmRanges OBJECT-TYPE
        SYNTAX DisplayString (SIZE(1..1000))
        ACCESS read-write
        STATUS mandatory
        DESCRIPTION
     "The ranges and associated server groups for the tuxDmRoutingFieldType routing
     field. The format of the string is a comma-separated, ordered list of
     range/group name pairs. A range/group name pair has the following
     format:

     lower[-upper]:raccesspoint

     lower and upper are signed numeric values or character strings in
     single quotes. lower must be less than or equal to upper. To embed a
     single quote in a character string value, it must be preceded by two
     backslashes (for example, 'O\\'Brien'). The value MIN can be used to
     indicate the minimum value for the data type of the associated field on
     the machine. The value MAX can be used to indicate the maximum value
     for the data type of the associated field on the machine. Thus,
     'MIN--5' is all numbers less than or equal to -5, and '6-MAX' is all
     numbers greater than or equal to 6.

     The meta-character '*' (wild-card) in the position of a range indicates
     any values not covered by the other ranges previously seen in the
     entry. Only one wild-card range is allowed per entry and it should be
     last (ranges following it are ignored).

     The routing field can be of any data type supported in FML. A numeric
     routing field must have numeric range values, and a string routing
     field must have string range values.

     String range values for string, carray, and character field types must
     be placed inside a pair of single quotes and cannot be preceded by a
     sign. Short and long integer values are a string of digits, optionally
     preceded by a plus or minus sign. Floating point numbers are of the
     form accepted by the C compiler or atof(3): an optional sign, then a
     string of digits optionally containing a decimal point, then an
     optional e or E followed by an optional sign or space, followed by an
     integer.

     The raccesspoint parameter indicates the remote domain access point to
     which the request is routed if the field matches the range. A
     raccesspoint of '*' indicates that the request can go to any remote
     domain access point that imports the desired service."
        ::= { tuxDmRoutingEntry 50 }

tuxDmRoutingState OBJECT-TYPE
        SYNTAX INTEGER {
                valid(1),
                invalid(2)
        }
        ACCESS read-write
        STATUS mandatory
        DESCRIPTION
     " This object denotes the current state of the tuxDmRouting instance.
     GET requests: 
           valid      The object exists.

     SET requests: 

           invalid    The object is deleted."
        ::= { tuxDmRoutingEntry 60 }

-- tuxDmrPrincipal Table

tuxDmrPrincipalTable OBJECT-TYPE
        SYNTAX SEQUENCE OF TuxDmrPrincipalEntry
        ACCESS not-accessible
        STATUS mandatory
        DESCRIPTION
	"This group represents password configuration information for
	remote principal names."
        ::= { tuxDmrPrincipal 1 }
 
tuxDmrPrincipalEntry OBJECT-TYPE
        SYNTAX TuxDmrPrincipalEntry
        ACCESS not-accessible
        STATUS mandatory
        DESCRIPTION
	"This group represents password configuration information for
	remote principal names."
        INDEX   { tuxDmrPrincipalDmrAccessPoint, tuxDmrPrincipalDmrPrinName }
        ::= { tuxDmrPrincipalTable 1 }
 
TuxDmrPrincipalEntry ::= SEQUENCE {
        tuxDmrPrincipalDmrAccessPoint
                DisplayString,
        tuxDmrPrincipalDmrPrinName
                DisplayString,
        tuxDmrPrincipalDmrPrinPasswd
                DisplayString,
        tuxDmrPrincipalState
                INTEGER
        }

tuxDmrPrincipalDmrAccessPoint OBJECT-TYPE
        SYNTAX DisplayString (SIZE(1..24))
        ACCESS read-only
        STATUS mandatory
        DESCRIPTION
     "The remote domain access point to which the principal is applicable."
        ::= { tuxDmrPrincipalEntry 10 }
 
tuxDmrPrincipalDmrPrinName OBJECT-TYPE
        SYNTAX DisplayString (SIZE(1..24))
        ACCESS read-only
        STATUS mandatory
        DESCRIPTION
     "The remote principal name."
        ::= { tuxDmrPrincipalEntry 20 }

tuxDmrPrincipalDmrPrinPasswd OBJECT-TYPE
        SYNTAX DisplayString (SIZE(0..8))
        ACCESS write-only
        STATUS mandatory
        DESCRIPTION
     "The remote password to be used for the principal name when
     communicating through the remote domain access point identified in
     tuxDmrPrincipalDmrAccessPoint."
        ::= { tuxDmrPrincipalEntry 30 }

tuxDmrPrincipalState OBJECT-TYPE
        SYNTAX INTEGER {
                valid(1),
                invalid(2)
        }
        ACCESS read-write
        STATUS mandatory
        DESCRIPTION
     " This object denotes the current state of the tuxDmrPrincipal instance.
     GET requests: 
           valid      The object exists.

     SET requests: 

           invalid    The object is deleted."
        ::= { tuxDmrPrincipalEntry 40 }

-- tuxDmSnaCRM Table

tuxDmSnaCRMTable OBJECT-TYPE
        SYNTAX SEQUENCE OF TuxDmSnaCRMEntry
        ACCESS not-accessible
        STATUS mandatory
        DESCRIPTION
	"This group defines the SNA-CRM-specific configuration for the
	named local domain access point."
        ::= { tuxDmSnaCRM 1 }
 
tuxDmSnaCRMEntry OBJECT-TYPE
        SYNTAX TuxDmSnaCRMEntry
        ACCESS not-accessible
        STATUS mandatory
        DESCRIPTION
	"This group defines the SNA-CRM-specific configuration for the
	named local domain access point."
        INDEX   { tuxDmSnaCRMDmSNACRM }
        ::= { tuxDmSnaCRMTable 1 }
 
TuxDmSnaCRMEntry ::= SEQUENCE {
        tuxDmSnaCRMDmSNACRM
                DisplayString,
        tuxDmSnaCRMDmlAccessPoint
                DisplayString,
        tuxDmSnaCRMState
                INTEGER,
        tuxDmSnaCRMDmNWAddr
                DisplayString,
        tuxDmSnaCRMDmNWDevice
                DisplayString
        }

tuxDmSnaCRMDmSNACRM OBJECT-TYPE
        SYNTAX DisplayString (SIZE(1..30))
        ACCESS read-only
        STATUS mandatory
        DESCRIPTION
     "this is an identifier unique within the scope of the SNA CRM entries 
	within the domain configuration
     used to identify this SNA CRM entry."
        ::= { tuxDmSnaCRMEntry 10 }
 
tuxDmSnaCRMDmlAccessPoint OBJECT-TYPE
        SYNTAX DisplayString (SIZE(1..30))
        ACCESS write-only
        STATUS mandatory
        DESCRIPTION
     "The name of the local domain access point entry with which this SNA CRM
     is used."
        ::= { tuxDmSnaCRMEntry 20 }

tuxDmSnaCRMState OBJECT-TYPE
        SYNTAX INTEGER {
                valid(1),
                invalid(2)
        }
        ACCESS read-write
        STATUS mandatory
        DESCRIPTION
     " This object denotes the current state of the tuxDmSnaCRM instance.
     GET requests: 
           valid      The object exists.

     SET requests: 

           invalid    The object is deleted."
        ::= { tuxDmSnaCRMEntry 30 }

tuxDmSnaCRMDmNWAddr OBJECT-TYPE
        SYNTAX DisplayString (SIZE(1..78))
        ACCESS read-write
        STATUS mandatory
        DESCRIPTION
     "Specifies the network address for communication between the domain
     gateway for the local domain access point and the SNA CRM."
        ::= { tuxDmSnaCRMEntry 40 }

tuxDmSnaCRMDmNWDevice OBJECT-TYPE
        SYNTAX DisplayString (SIZE(1..78))
        ACCESS read-write
        STATUS mandatory
        DESCRIPTION
     "Specifies the network device to be used for communication between the
     domain gateway for the local domain access point and the SNA CRM."
        ::= { tuxDmSnaCRMEntry 50 }

-- tuxDmSnaLink Table

tuxDmSnaLinkTable OBJECT-TYPE
        SYNTAX SEQUENCE OF TuxDmSnaLinkEntry
        ACCESS not-accessible
        STATUS mandatory
        DESCRIPTION
	"This group represents snax-specific configuration information
	for a remote domain access point."
        ::= { tuxDmSnaLink 1 }
 
tuxDmSnaLinkEntry OBJECT-TYPE
        SYNTAX TuxDmSnaLinkEntry
        ACCESS not-accessible
        STATUS mandatory
        DESCRIPTION
	"This group class represents snax-specific configuration information
	for a remote domain access point."
        INDEX   { tuxDmSnaLinkDmSNALink }
        ::= { tuxDmSnaLinkTable 1 }
 
TuxDmSnaLinkEntry ::= SEQUENCE {
        tuxDmSnaLinkDmSNALink
                DisplayString,
        tuxDmSnaLinkDmSNAStack
                DisplayString,
        tuxDmSnaLinkDmrAccessPoint
                DisplayString,
        tuxDmSnaLinkDmlSysID
                DisplayString,
        tuxDmSnaLinkDmrSysID
                DisplayString,
        tuxDmSnaLinkDmlUname
                DisplayString,
        tuxDmSnaLinkDmMinWin
                INTEGER,
        tuxDmSnaLinkDmModeName
                DisplayString,
        tuxDmSnaLinkState
                INTEGER,
        tuxDmSnaLinkDmSecType
                INTEGER,
        tuxDmSnaLinkDmStartType
                INTEGER,
        tuxDmSnaLinkDmMaxSNAsess
                INTEGER,
        tuxDmSnaLinkDmMaxSyncLvl
                INTEGER
        }

tuxDmSnaLinkDmSNALink OBJECT-TYPE
        SYNTAX DisplayString (SIZE(1..30))
        ACCESS read-only
        STATUS mandatory
        DESCRIPTION
     "This is an identifier, unique within the
     scope of the SNA LINK entries within the domain configuration, used to
     identify rows in this table"
        ::= { tuxDmSnaLinkEntry 10 }
 
tuxDmSnaLinkDmSNAStack OBJECT-TYPE
        SYNTAX DisplayString (SIZE(1..30))
        ACCESS read-write
        STATUS mandatory
        DESCRIPTION
     "The name of the snax stack entry to be used to reach this remote domain
     access point."
        ::= { tuxDmSnaLinkEntry 20 }
 
tuxDmSnaLinkDmrAccessPoint OBJECT-TYPE
        SYNTAX DisplayString (SIZE(1..30))
        ACCESS read-write
        STATUS mandatory
        DESCRIPTION
     "Identifies the remote domain access point name for which this entry
     provides the snax configuration data."
        ::= { tuxDmSnaLinkEntry 30 }

tuxDmSnaLinkDmlSysID OBJECT-TYPE
        SYNTAX DisplayString (SIZE(1..4))
        ACCESS read-write
        STATUS mandatory
        DESCRIPTION
     "The local SYSID to be used when establishing an SNA link to the remote
     logical unit (LU)."
        ::= { tuxDmSnaLinkEntry 40 }

tuxDmSnaLinkDmrSysID OBJECT-TYPE
        SYNTAX DisplayString (SIZE(1..4))
        ACCESS read-write
        STATUS mandatory
        DESCRIPTION
     "The remote SYSID to be used when establishing an SNA link to the remote
     LU."
        ::= { tuxDmSnaLinkEntry 50 }

tuxDmSnaLinkDmlUname OBJECT-TYPE
        SYNTAX DisplayString (SIZE(1..8))
        ACCESS read-write
        STATUS mandatory
        DESCRIPTION
     "Specifies the LU name associated with the remote domain access point."
        ::= { tuxDmSnaLinkEntry 60 }

tuxDmSnaLinkDmMinWin OBJECT-TYPE
        SYNTAX INTEGER
        ACCESS read-write
        STATUS mandatory
        DESCRIPTION
     "The minimum number of winner sessions to the remote LU."
        ::= { tuxDmSnaLinkEntry 70 }

tuxDmSnaLinkDmModeName OBJECT-TYPE
        SYNTAX DisplayString (SIZE(1..8))
        ACCESS read-write
        STATUS mandatory
        DESCRIPTION
     "Specifies the name associated with the session characteristics for
     sessions to the remote LU."
        ::= { tuxDmSnaLinkEntry 80 }

tuxDmSnaLinkState OBJECT-TYPE
        SYNTAX INTEGER {
                valid(1),
                invalid(2)
        }
        ACCESS read-write
        STATUS mandatory
        DESCRIPTION
     " This object denotes the current state of the tuxDmSnaLink instance.
     GET requests: 
           valid      The object exists.

     SET requests: 

           invalid    The object is deleted."
        ::= { tuxDmSnaLinkEntry 90 }

tuxDmSnaLinkDmSecType OBJECT-TYPE
        SYNTAX INTEGER {
                local(1),
                identity(2),
                verify(3),
                persistent(4),
                mixidpe(5)
        }
        ACCESS read-write
        STATUS mandatory
        DESCRIPTION
     "Specifies the type of SNA security to be used on sessions to the remote
     LU. Valid values for this attribute are local, identify, verify,
     persistent, AND mixidpe."
        ::= { tuxDmSnaLinkEntry 100 }

tuxDmSnaLinkDmStartType OBJECT-TYPE
        SYNTAX INTEGER {
                auto(1),
                cold(2)
        }
        ACCESS read-write
        STATUS mandatory
        DESCRIPTION
     "Specifies the type of session start-up for the destination LU. Setting
     this attribute to cold forces a COLDSTART with the LU. If set to Auto,
     the SNACRM in conjunction with the domain gateway choose whether to
     COLDSTART or WARMSTART the LU."
        ::= { tuxDmSnaLinkEntry 110 }

tuxDmSnaLinkDmMaxSNAsess OBJECT-TYPE
        SYNTAX INTEGER  (0..32767)
        ACCESS read-write
        STATUS mandatory
        DESCRIPTION
     "Specifies maximum number of sessions to establish with the remote LU."
        ::= { tuxDmSnaLinkEntry 120 }

tuxDmSnaLinkDmMaxSyncLvl OBJECT-TYPE
        SYNTAX INTEGER (0..2)
        ACCESS read-only
        STATUS mandatory
        DESCRIPTION
     "The maximum SYNC LEVEL that can be supported to this remote LU."
        ::= { tuxDmSnaLinkEntry 130 }

-- tuxDmSnaStack Table

tuxDmSnaStackTable OBJECT-TYPE
        SYNTAX SEQUENCE OF TuxDmSnaStackEntry
        ACCESS not-accessible
        STATUS mandatory
        DESCRIPTION
	"This group defines an SNA stack to be used by a specific SNA
	CRM."
        ::= { tuxDmSnaStack 1 }
 
tuxDmSnaStackEntry OBJECT-TYPE
        SYNTAX TuxDmSnaStackEntry
        ACCESS not-accessible
        STATUS mandatory
        DESCRIPTION
	"This group defines an SNA stack to be used by a specific SNA
	CRM."
        INDEX   { tuxDmSnaStackDmSnaStack }
        ::= { tuxDmSnaStackTable 1 }
 
TuxDmSnaStackEntry ::= SEQUENCE {
        tuxDmSnaStackDmSnaStack
                DisplayString,
        tuxDmSnaStackDmSnaCRM
                DisplayString,
        tuxDmSnaStackDmStackType
                DisplayString,
        tuxDmSnaStackDmlUname
                DisplayString,
        tuxDmSnaStackDmTpName
                DisplayString,
        tuxDmSnaStackDmStackParams
                DisplayString,
        tuxDmSnaStackState
                INTEGER
        }

tuxDmSnaStackDmSnaStack OBJECT-TYPE
        SYNTAX DisplayString (SIZE(1..30))
        ACCESS read-only
        STATUS mandatory
        DESCRIPTION
     "This is an identifier
     unique within the scope of tuxDmSnaStack Table the domain
     configuration."
        ::= { tuxDmSnaStackEntry 10 }
 
tuxDmSnaStackDmSnaCRM OBJECT-TYPE
        SYNTAX DisplayString (SIZE(1..30))
        ACCESS read-write
        STATUS mandatory
        DESCRIPTION
     "Identifies the eaDmSnaCRM Table entry of the SNA CRM in which this SNA
     protocol stack definition is used."
        ::= { tuxDmSnaStackEntry 20 }
 
tuxDmSnaStackDmStackType OBJECT-TYPE
        SYNTAX DisplayString (SIZE(1..30))
        ACCESS read-write
        STATUS mandatory
        DESCRIPTION
     "Identifies the protocol stack to be used."
        ::= { tuxDmSnaStackEntry 30 }

tuxDmSnaStackDmlUname OBJECT-TYPE
        SYNTAX DisplayString (SIZE(1..8))
        ACCESS read-write
        STATUS mandatory
        DESCRIPTION
     "Specifies the LU name to be used on sessions established using this
     stack definition."
        ::= { tuxDmSnaStackEntry 40 }

tuxDmSnaStackDmTpName OBJECT-TYPE
        SYNTAX DisplayString (SIZE(1..8))
        ACCESS read-write
        STATUS mandatory
        DESCRIPTION
     "Specifies the TP name associated with the SNA stack. A value of '*'
     means accept any TP name."
        ::= { tuxDmSnaStackEntry 50 }

tuxDmSnaStackDmStackParams OBJECT-TYPE
        SYNTAX DisplayString (SIZE(1..128))
        ACCESS read-write
        STATUS mandatory
        DESCRIPTION
     "Provides protocol stack specific parameters."
        ::= { tuxDmSnaStackEntry 60 }

tuxDmSnaStackState OBJECT-TYPE
        SYNTAX INTEGER {
                valid(1),
                invalid(2)
        }
        ACCESS read-write
        STATUS mandatory
        DESCRIPTION
     " This object denotes the current state of the tuxDmSnaStack instance.
     GET requests: 
           valid      The object exists.

     SET requests: 

           invalid    The object is deleted."
        ::= { tuxDmSnaStackEntry 70 }

-- Taken out as it is no more defined in the new Tux7.1 dmmib(5)
-- tuxDmStatistics Table
--  
-- tuxDmStatisticsTable OBJECT-TYPE
--         SYNTAX SEQUENCE OF TuxDmStatisticsEntry
--         ACCESS not-accessible
--         STATUS mandatory
--         DESCRIPTION
-- 	"This group represents run-time statistical information about
-- 	a local domain access point."
--         ::= { tuxDmStatistics 1 }
--  
-- tuxDmStatisticsEntry OBJECT-TYPE
--         SYNTAX TuxDmStatisticsEntry
--         ACCESS not-accessible
--         STATUS mandatory
--         DESCRIPTION
-- 	"This group represents run-time statistical information about
-- 	a local domain access point."
--         INDEX   { tuxDmStatisticsDmlAccessPoint }
--         ::= { tuxDmStatisticsTable 1 }
--  
-- TuxDmStatisticsEntry ::= SEQUENCE {
--         tuxDmStatisticsDmlAccessPoint
--                 DisplayString,
--         tuxDmStatisticsState
--                 INTEGER,
--         tuxDmStatisticsDmAudit
--                 INTEGER,
--         tuxDmStatisticsDmEvNumAct
--                 INTEGER,
--         tuxDmStatisticsDmEvNumSuspn
--                 INTEGER,
--         tuxDmStatisticsDmEvNumSuspt
--                 INTEGER,
--         tuxDmStatisticsDmcwlConNumAct
--                 INTEGER,
--         tuxDmStatisticsDmlConNumRcv
--                 INTEGER,
--         tuxDmStatisticsDmlConNumSnd
--                 INTEGER,
--         tuxDmStatisticsDmlConvTot
--                 INTEGER,
--         tuxDmStatisticsDmlConvTotfail
--                 INTEGER,
--         tuxDmStatisticsDmlConvTotRcv
--                 INTEGER,
--         tuxDmStatisticsDmlConvTotSnd
--                 INTEGER,
--         tuxDmStatisticsDmlSvcNumAct
--                 INTEGER,
--         tuxDmStatisticsDmlSvcTot
--                 INTEGER,
--         tuxDmStatisticsDmlSvcTotFail	
--                 INTEGER,
--         tuxDmStatisticsDmlSvcTotRply
--                 INTEGER,
--         tuxDmStatisticsDmLogContentions
--                 INTEGER,
--         tuxDmStatisticsDmrConvNumAct
--                 INTEGER,
--         tuxDmStatisticsDmrConvNumRcv
--                 INTEGER,
--         tuxDmStatisticsDmrConvNumSnd
--                 INTEGER,
--         tuxDmStatisticsDmrConvTot
--                 INTEGER,
--         tuxDmStatisticsDmrConvTotfail
--                 INTEGER,
--         tuxDmStatisticsDmrConvTotRcv
--                 INTEGER,
--         tuxDmStatisticsDmrConvTotSnd
--                 INTEGER,
--         tuxDmStatisticsDmrSvcNumAct
--                 INTEGER,
--         tuxDmStatisticsDmrSvcTot
--                 INTEGER,
--         tuxDmStatisticsDmrSvcTotFail	
--                 INTEGER,
--         tuxDmStatisticsDmrSvcTotRply
--                 INTEGER,
--         tuxDmStatisticsDmShmContentions
--                 INTEGER,
--         tuxDmStatisticsDmStatResetTime
--                 INTEGER,
--         tuxDmStatisticsDmTxNumAct
--                 INTEGER,
--         tuxDmStatisticsDmTxTotBegun
--                 INTEGER,
--         tuxDmStatisticsDmTxTotCommit
--                 INTEGER,
--         tuxDmStatisticsDmTxTotHCommit
--                 INTEGER,
--         tuxDmStatisticsDmTxTotHRlbk
--                 INTEGER,
--         tuxDmStatisticsDmTxTotRlbk
--                 INTEGER
--         }
-- 
-- 
-- tuxDmStatisticsDmlAccessPoint OBJECT-TYPE
--         SYNTAX DisplayString (SIZE(1..30))
--         ACCESS read-only
--         STATUS mandatory
--         DESCRIPTION
--      "The name of local domain access point. Other attributes represent
--      statistical information for this local domain access point."
--         ::= { tuxDmStatisticsEntry 1 }
--  
-- tuxDmStatisticsState OBJECT-TYPE
--         SYNTAX INTEGER {
--                 active(1),
--                 inactive(2),
--                 reset(3)
--         }
--         ACCESS read-write
--         STATUS mandatory
--         DESCRIPTION
--      " This object denotes the current state of the tuxDmStatistics instance.
--      GET requests: 
--            active    Statistics gathering is active (enabled) for the
--                      identified local domain access point.
--            inactive  Statistics gathering is not active (disabled) for the
--                      identified local domain access point.
-- 
--      SET requests: 
-- 
--            active:    Statistics gathering is enabled for the identified
--                       local domain access point. This state change is
--                       allowed in the state INActive and results in the
--                       state ACTive.
--            inactive:  Statistics gathering is disabled for the identified
--                       local domain access point. This state change is
--                       allowed in the state ACTive and results in the state
--                       INActive.
--            reset:     All statistics values are reset. This value is
--                       allowed in the states ACTive and INActive and no
--                       state change results."
--         ::= { tuxDmStatisticsEntry 2 }
-- 
-- tuxDmStatisticsDmAudit OBJECT-TYPE
--         SYNTAX INTEGER {
--                 on(1),
--                 off(2)
--         }
--         ACCESS read-write
--         STATUS mandatory
--         DESCRIPTION
--      "This attribute is used to enable or disable run-time auditing on a
--      local domain access point. If on, then auditing is enabled; if off,
--      then auditing is disabled. This attribute may be SET in order to change
--      the auditing state."
--         ::= { tuxDmStatisticsEntry 3 }
-- 
-- tuxDmStatisticsDmEvNumAct OBJECT-TYPE
--         SYNTAX INTEGER
--         ACCESS read-only
--         STATUS mandatory
--         DESCRIPTION
--      "The number of active internal events within the domain gateway
--      supporting the local domain access point."
--         ::= { tuxDmStatisticsEntry 4 }
--  
-- tuxDmStatisticsDmEvNumSuspn OBJECT-TYPE
--         SYNTAX INTEGER
--         ACCESS read-only
--         STATUS mandatory
--         DESCRIPTION
--      "The number of internal events suspended on the BEA Tuxedo system within
--      the domain gateway supporting the local domain access point."
--         ::= { tuxDmStatisticsEntry 5 }
--  
-- 
-- tuxDmStatisticsDmEvNumSuspt OBJECT-TYPE
--         SYNTAX INTEGER
--         ACCESS read-only
--         STATUS mandatory
--         DESCRIPTION
--      "The number of internal events suspended on the network within the
--      domain gateway supporting the local domain access point."
--         ::= { tuxDmStatisticsEntry 6 }
--  
-- tuxDmStatisticsDmcwlConNumAct OBJECT-TYPE
--         SYNTAX INTEGER
--         ACCESS read-only
--         STATUS mandatory
--         DESCRIPTION
--      "The number of active conversations with local services."
--         ::= { tuxDmStatisticsEntry 7 }
--  
-- tuxDmStatisticsDmlConNumRcv OBJECT-TYPE
--         SYNTAX INTEGER
--         ACCESS read-only
--         STATUS mandatory
--         DESCRIPTION
--      "The number of receives by active conversations with local services."
--         ::= { tuxDmStatisticsEntry 8 }
--  
-- tuxDmStatisticsDmlConNumSnd OBJECT-TYPE
--         SYNTAX INTEGER
--         ACCESS read-only
--         STATUS mandatory
--         DESCRIPTION
--      "The number of sends by active conversations with local services."
--         ::= { tuxDmStatisticsEntry 9 }
--  
-- tuxDmStatisticsDmlConvTot OBJECT-TYPE
--         SYNTAX INTEGER
--         ACCESS read-only
--         STATUS mandatory
--         DESCRIPTION
--      "The total number of completed conversations with local services."
--         ::= { tuxDmStatisticsEntry 10 }
--  
-- tuxDmStatisticsDmlConvTotfail OBJECT-TYPE
--         SYNTAX INTEGER
--         ACCESS read-only
--         STATUS mandatory
--         DESCRIPTION
--      "The total number of completed conversations with local services that
--      abnormally disconnected."
--         ::= { tuxDmStatisticsEntry 11 }
--  
-- 
-- tuxDmStatisticsDmlConvTotRcv OBJECT-TYPE
--         SYNTAX INTEGER
--         ACCESS read-only
--         STATUS mandatory
--         DESCRIPTION
--      "The total number of receives by completed conversations with local
--      services."
--         ::= { tuxDmStatisticsEntry 12 }
--  
-- tuxDmStatisticsDmlConvTotSnd OBJECT-TYPE
--         SYNTAX INTEGER
--         ACCESS read-only
--         STATUS mandatory
--         DESCRIPTION
--      "The total number of sends by completed conversations with local
--      services."
--         ::= { tuxDmStatisticsEntry 13 }
--  
-- tuxDmStatisticsDmlSvcNumAct OBJECT-TYPE
--         SYNTAX INTEGER
--         ACCESS read-only
--         STATUS mandatory
--         DESCRIPTION
--      "The number of active requests to local services."
--         ::= { tuxDmStatisticsEntry 14 }
--  
-- tuxDmStatisticsDmlSvcTot OBJECT-TYPE
--         SYNTAX INTEGER
--         ACCESS read-only
--         STATUS mandatory
--         DESCRIPTION
--      "The total number of completed requests to local services."
--         ::= { tuxDmStatisticsEntry 15 }
--  
-- tuxDmStatisticsDmlSvcTotFail OBJECT-TYPE
--         SYNTAX INTEGER
--         ACCESS read-only
--         STATUS mandatory
--         DESCRIPTION
--      "The total number of requests to local services that failed."
--         ::= { tuxDmStatisticsEntry 16 }
--  
-- tuxDmStatisticsDmlSvcTotRply OBJECT-TYPE
--         SYNTAX INTEGER
--         ACCESS read-only
--         STATUS mandatory
--         DESCRIPTION
--      "The total number of completed requests to local services that received
--      a successful reply."
--         ::= { tuxDmStatisticsEntry 17 }
--  
-- tuxDmStatisticsDmLogContentions OBJECT-TYPE
--         SYNTAX INTEGER
--         ACCESS read-only
--         STATUS mandatory
--         DESCRIPTION
--      "The number of contentions for log records."
--         ::= { tuxDmStatisticsEntry 18 }
--  
-- tuxDmStatisticsDmrConvNumAct OBJECT-TYPE
--         SYNTAX INTEGER
--         ACCESS read-only
--         STATUS mandatory
--         DESCRIPTION
--      "The number of active conversations with remote services."
--         ::= { tuxDmStatisticsEntry 19 }
--  
-- tuxDmStatisticsDmrConvNumRcv OBJECT-TYPE
--         SYNTAX INTEGER
--         ACCESS read-only
--         STATUS mandatory
--         DESCRIPTION
--      "The number of receives by active conversations with remote services."
--         ::= { tuxDmStatisticsEntry 20 }
--  
-- tuxDmStatisticsDmrConvNumSnd OBJECT-TYPE
--         SYNTAX INTEGER
--         ACCESS read-only
--         STATUS mandatory
--         DESCRIPTION
--      "The number of sends by active conversations with remote services."
--         ::= { tuxDmStatisticsEntry 21 }
--  
-- tuxDmStatisticsDmrConvTot OBJECT-TYPE
--         SYNTAX INTEGER
--         ACCESS read-only
--         STATUS mandatory
--         DESCRIPTION
--      "The total number of completed conversations with remote services."
--         ::= { tuxDmStatisticsEntry 22 }
--  
-- tuxDmStatisticsDmrConvTotfail OBJECT-TYPE
--         SYNTAX INTEGER
--         ACCESS read-only
--         STATUS mandatory
--         DESCRIPTION
--      "The total number of completed conversations with remote services that
--      abnormally disconnected."
--         ::= { tuxDmStatisticsEntry 23 }
--  
-- tuxDmStatisticsDmrConvTotRcv OBJECT-TYPE
--         SYNTAX INTEGER
--         ACCESS read-only
--         STATUS mandatory
--         DESCRIPTION
--      "The total number of receives by completed conversations with remote
--      services."
--         ::= { tuxDmStatisticsEntry 24 }
--  
-- tuxDmStatisticsDmrConvTotSnd OBJECT-TYPE
--         SYNTAX INTEGER
--         ACCESS read-only
--         STATUS mandatory
--         DESCRIPTION
--      "The total number of sends by completed conversations with remote
--      services."
--         ::= { tuxDmStatisticsEntry 25 }
--  
-- tuxDmStatisticsDmrSvcNumAct OBJECT-TYPE
--         SYNTAX INTEGER
--         ACCESS read-only
--         STATUS mandatory
--         DESCRIPTION
--      "The number of active requests to remote services."
--         ::= { tuxDmStatisticsEntry 26 }
--  
-- 
-- tuxDmStatisticsDmrSvcTot OBJECT-TYPE
--         SYNTAX INTEGER
--         ACCESS read-only
--         STATUS mandatory
--         DESCRIPTION
--      "The total number of completed requests to remote services."
--         ::= { tuxDmStatisticsEntry 27 }
--  
-- tuxDmStatisticsDmrSvcTotFail OBJECT-TYPE
--         SYNTAX INTEGER
--         ACCESS read-only
--         STATUS mandatory
--         DESCRIPTION
--      "The total number of requests to remote services that failed."
--         ::= { tuxDmStatisticsEntry 28 }
--  
-- tuxDmStatisticsDmrSvcTotRply OBJECT-TYPE
--         SYNTAX INTEGER
--         ACCESS read-only
--         STATUS mandatory
--         DESCRIPTION
--      "The total number of completed requests to remote services that received
--      a successful reply."
--         ::= { tuxDmStatisticsEntry 29 }
--  
-- tuxDmStatisticsDmShmContentions OBJECT-TYPE
--         SYNTAX INTEGER
--         ACCESS read-only
--         STATUS mandatory
--         DESCRIPTION
--      "The number of contentions for shared memory locks."
--         ::= { tuxDmStatisticsEntry 30 }
--  
-- tuxDmStatisticsDmStatResetTime OBJECT-TYPE
--         SYNTAX INTEGER
--         ACCESS read-only
--         STATUS mandatory
--         DESCRIPTION
--      "The time the statistics were last reset."
--         ::= { tuxDmStatisticsEntry 31 }
--  
-- tuxDmStatisticsDmTxNumAct OBJECT-TYPE
--         SYNTAX INTEGER
--         ACCESS read-only
--         STATUS mandatory
--         DESCRIPTION
--      "The number of active transactions."
--         ::= { tuxDmStatisticsEntry 32 }
--  
-- 
-- tuxDmStatisticsDmTxTotBegun OBJECT-TYPE
--         SYNTAX INTEGER
--         ACCESS read-only
--         STATUS mandatory
--         DESCRIPTION
--      "The number of transactions that have been started."
--         ::= { tuxDmStatisticsEntry 33 }
--  
-- tuxDmStatisticsDmTxTotCommit OBJECT-TYPE
--         SYNTAX INTEGER
--         ACCESS read-only
--         STATUS mandatory
--         DESCRIPTION
--      "The number of transactions that were committed."
--         ::= { tuxDmStatisticsEntry 34 }
--  
-- tuxDmStatisticsDmTxTotHCommit OBJECT-TYPE
--         SYNTAX INTEGER
--         ACCESS read-only
--         STATUS mandatory
--         DESCRIPTION
--      "The number of transactions that were heuristically committed."
--         ::= { tuxDmStatisticsEntry 35 }
--  
-- tuxDmStatisticsDmTxTotHRlbk OBJECT-TYPE
--         SYNTAX INTEGER
--         ACCESS read-only
--         STATUS mandatory
--         DESCRIPTION
--      "The number of transactions that were heuristically rolled back."
--         ::= { tuxDmStatisticsEntry 36 }
--  
-- tuxDmStatisticsDmTxTotRlbk OBJECT-TYPE
--         SYNTAX INTEGER
--         ACCESS read-only
--         STATUS mandatory
--         DESCRIPTION
--      "The number of transactions that were rolled back."
--         ::= { tuxDmStatisticsEntry 37 }
-- 

-- tuxDmTdomain Table

tuxDmTdomainTable OBJECT-TYPE
        SYNTAX SEQUENCE OF TuxDmTdomainEntry
        ACCESS not-accessible
        STATUS mandatory
        DESCRIPTION
	"This group defines the TDomain specific configuration for a
	local or remote domain access point."
        ::= { tuxDmTdomain 1 }
 
tuxDmTdomainEntry OBJECT-TYPE
        SYNTAX TuxDmTdomainEntry
        ACCESS not-accessible
        STATUS mandatory
        DESCRIPTION
	"This group defines the TDomain specific configuration for a
	local or remote domain access point."
        INDEX   { tuxDmTdomainDmAccessPoint, tuxDmTdomainDmNwAddr }
        ::= { tuxDmTdomainTable 1 }
 
TuxDmTdomainEntry ::= SEQUENCE {
        tuxDmTdomainDmAccessPoint
                DisplayString,
        tuxDmTdomainDmNwAddr
                DisplayString,
        tuxDmTdomainState
                INTEGER,
        tuxDmTdomainDmNwDevice
                DisplayString,
        tuxDmTdomainDmCmpLimit
                INTEGER,
        tuxDmTdomainDmFailOverSeq
                INTEGER,
        tuxDmTdomainDmMinEncriptBits
                INTEGER,
        tuxDmTdomainDmMaxEncriptBits
                INTEGER
        }



tuxDmTdomainDmAccessPoint OBJECT-TYPE
        SYNTAX DisplayString (SIZE(1..24))
        ACCESS read-only
        STATUS mandatory
        DESCRIPTION
     "The local or remote domain access point name for which this entry
     provides the TDomain-specific configuration data.

     When domain level failover is in use, more than one tuxDmTdomain Table
     entries can be defined with the same tuxDmTdomainDmAccessPoint"
        ::= { tuxDmTdomainEntry 10 }
 
tuxDmTdomainDmNwAddr OBJECT-TYPE
        SYNTAX DisplayString (SIZE(1..24))
        ACCESS read-only
        STATUS mandatory
        DESCRIPTION
     "Specifies the network address associated with the access point. For a
     local domain access point, this attribute supplies the address to be
     used for listening for incoming connections. For a remote domain access
     point, this attribute supplies the destination address to be used when
     connecting to a remote domain access point. The value of this field
     must be unique across all tuxDmTdomainTable entries."
        ::= { tuxDmTdomainEntry 20 }
 
tuxDmTdomainState OBJECT-TYPE
        SYNTAX INTEGER {
                valid(1),
                invalid(2)
        }
        ACCESS read-write
        STATUS mandatory
        DESCRIPTION
     " This object denotes the current state of the tuxDmTdomain instance.
     GET requests: 
           valid    only exists

     SET requests: 

           invalid:    delete the object"
        ::= { tuxDmTdomainEntry 30 }

tuxDmTdomainDmNwDevice OBJECT-TYPE
        SYNTAX DisplayString (SIZE(1..78))
        ACCESS read-write
        STATUS mandatory
        DESCRIPTION
     "Specifies the network device to be used. For a local domain access
     point, this attribute specifies the device to be used for listening.
     For a remote domain access point, this attribute specifies the device
     to be used when connecting to the remote domain access point."
        ::= { tuxDmTdomainEntry 40 }
 

tuxDmTdomainDmCmpLimit OBJECT-TYPE
        SYNTAX INTEGER
        ACCESS read-write
        STATUS mandatory
        DESCRIPTION
     "Relevant to remote domain access points only. Specifies the threshold
     over which compression occurs for traffic on connections to this access
     point."
        ::= { tuxDmTdomainEntry 50 }

tuxDmTdomainDmFailOverSeq OBJECT-TYPE
        SYNTAX INTEGER (0..32767)
        ACCESS read-write
        STATUS mandatory
        DESCRIPTION
     "Relevant to remote domain access points only. Specifies the position of
     this set of addressing in the failover sequence for this remote domain
     access point. If no failover sequence number is supplied, the first
     entry for this remote domain access point is allocated the number 10
     greater than the highest failover sequence number known for the remote
     domain access point. Thus, the first entry gets 10, the second 20, and
     so on.

     The domain gateway uses the tuxDmTdomainTable addressing entries for a
     particular remote domain access point strictly in the order of their
     failover sequence numbers - lowest to highest."
        ::= { tuxDmTdomainEntry 60 }

tuxDmTdomainDmMinEncriptBits OBJECT-TYPE
        SYNTAX INTEGER {
                enc-0-bit(1),
                enc-40-bits(2),
                enc-56-bits(3),
                enc-128-bits(4)
        }
        ACCESS read-write
        STATUS mandatory
        DESCRIPTION
     "Relevant to remote domain access points only. When establishing a
     network link to this access point, this attribute specifies the minimum
     level of encryption required. 'enc-0-bit' means no encryption; 'enc-40-bits', 'enc-56-bits', and
     'enc-128-bits' specify the encryption length (in bits). If this minimum level of
     encryption is not met, link establishment fails. The default value is
     'enc-0-bits'.

     Note: Modifications to this attribute do not affect established
     connections."
        ::= { tuxDmTdomainEntry 70 }

tuxDmTdomainDmMaxEncriptBits OBJECT-TYPE
        SYNTAX INTEGER {
                enc-0-bit(1),
                enc-40-bits(2),
                enc-56-bits(3),
                enc-128-bits(4)
        }
        ACCESS read-write
        STATUS mandatory
        DESCRIPTION
     "Relevant to remote domain access points only. When establishing a
     network link to this access point, this attribute specifies the maximum
     level of encryption allowed. '0' means no encryption; '40', '56', and
     '128' specify the encryption length (in bits). The default value is
     '128'.

     Note: Modifications to this attribute do not affect established
     connections."
        ::= { tuxDmTdomainEntry 80 }

-- tuxDmTopend Table

tuxDmTopendTable OBJECT-TYPE
        SYNTAX SEQUENCE OF TuxDmTopendEntry
        ACCESS not-accessible
        STATUS mandatory
        DESCRIPTION
	"This group defines the configuration for a local or remote domain
	access point specific to a BEA TOP END system."
        ::= { tuxDmTopend 1 }
 
tuxDmTopendEntry OBJECT-TYPE
        SYNTAX TuxDmTopendEntry
        ACCESS not-accessible
        STATUS mandatory
        DESCRIPTION
	"This group defines the configuration for a local or remote domain
	access point specific to a BEA TOP END system."
        INDEX   { tuxDmTopendDmAccessPoint, tuxDmTopendDmNwAddr }
        ::= { tuxDmTopendTable 1 }
 
TuxDmTopendEntry ::= SEQUENCE {
        tuxDmTopendDmAccessPoint
                DisplayString,
        tuxDmTopendDmNwAddr
                DisplayString,
        tuxDmTopendDmteTpSystem
                DisplayString,
        tuxDmTopendState
                INTEGER,
        tuxDmTopendDmNwDevice
                DisplayString,
        tuxDmTopendDmtePwd
                DisplayString,
        tuxDmTopendDmFailoverSeq
                INTEGER
        }



tuxDmTopendDmAccessPoint OBJECT-TYPE
        SYNTAX DisplayString (SIZE(1..24))
        ACCESS read-only
        STATUS mandatory
        DESCRIPTION
     "Specifies the local or remote domain access point name for which this
     entry provides the BEA TOP END system specific configuration data."
        ::= { tuxDmTopendEntry 10 }
 
tuxDmTopendDmNwAddr OBJECT-TYPE
        SYNTAX DisplayString (SIZE(1..24))
        ACCESS read-only
        STATUS mandatory
        DESCRIPTION
     "Specifies the network address associated with the local or remote
     domain access point."
        ::= { tuxDmTopendEntry 20 }
 
tuxDmTopendDmteTpSystem OBJECT-TYPE
        SYNTAX DisplayString (SIZE(1..8))
        ACCESS read-write
        STATUS mandatory
        DESCRIPTION
	""
        ::= { tuxDmTopendEntry 30 }
 
tuxDmTopendState OBJECT-TYPE
        SYNTAX INTEGER {
                valid(1),
                invalid(2),
                recrypt(3)
        }
        ACCESS read-write
        STATUS mandatory
        DESCRIPTION
     " This object denotes the current state of the tuxDmTopend instance.
     GET requests: 
           valid    Object exists

     SET requests: 

           invalid:    delete the object
           recrypt:  Re-encrypt all passwords using a new encryption key."
        ::= { tuxDmTopendEntry 40 }

tuxDmTopendDmNwDevice OBJECT-TYPE
        SYNTAX DisplayString (SIZE(1..78))
        ACCESS read-write
        STATUS mandatory
        DESCRIPTION
     "Specifies the network device associated with the local or remote domain
     access point."
        ::= { tuxDmTopendEntry 50 }
 

tuxDmTopendDmtePwd OBJECT-TYPE
        SYNTAX DisplayString (SIZE(1..12))
        ACCESS read-write
        STATUS mandatory
        DESCRIPTION
     "Specifies the password to be used when sending messages to the BEA TOP
     END system. Relevant only to local domain access point entries."
        ::= { tuxDmTopendEntry 60 }

tuxDmTopendDmFailoverSeq OBJECT-TYPE
        SYNTAX INTEGER (0..32767)
        ACCESS read-write
        STATUS mandatory
        DESCRIPTION
"Relevant to remote domain access points only. Specifies the position of this set of addressing in the failover sequence for this remote domain access point. If no failover sequence
     number is supplied, the first entry for this remote domain access point is allocated the number 10 greater than the highest failover sequence number known for the remote domain
     access point. Thus, the first entry gets 10, the second 20, and so on.

     The domain gateway uses the tuxDmTopend addressing entries for a particular remote domain access point strictly in the order of their failover sequence numbers - lowest to highest.

       Note: This attribute applies only to gateways running BEA Tuxedo Release 7.1 and is ignored by gateways running earlier releases of the BEA Tuxedo system."
        ::= { tuxDmTopendEntry 70 }

-- tuxDmTransaction Table

tuxDmTransactionTable OBJECT-TYPE
        SYNTAX SEQUENCE OF TuxDmTransactionEntry
        ACCESS not-accessible
        STATUS mandatory
        DESCRIPTION
	"This group represents information about transactions that
	span domains. This object can be used to find out what remote domain access
	points are involved in the transaction, the parent domain access point, the
	transaction state, and other information."
        ::= { tuxDmTransaction 1 }
 
tuxDmTransactionEntry OBJECT-TYPE
        SYNTAX TuxDmTransactionEntry
        ACCESS not-accessible
        STATUS mandatory
        DESCRIPTION
	"This group represents information about transactions that
	span domains. This object can be used to find out what remote domain access
	points are involved in the transaction, the parent domain access point, the
	transaction state, and other information."
        INDEX   { tuxDmTransactionDmlAccessPoint }
        ::= { tuxDmTransactionTable 1 }
 
TuxDmTransactionEntry ::= SEQUENCE {
        tuxDmTransactionDmlAccessPoint
                DisplayString,
        tuxDmTransactionDmTpTranID
                DisplayString,
        tuxDmTransactionState
                INTEGER,
        tuxDmTransactionDmTxAccessPoint
                DisplayString,
        tuxDmTransactionDmTxNetTranID
                DisplayString,
        tuxDmTransactionDmBranchCount
                INTEGER,
        tuxDmTransactionDmBranchIndex
                INTEGER,
        tuxDmTransactionDmBranchNo
                INTEGER,
        tuxDmTransactionDmrAccessPoint
                DisplayString,
        tuxDmTransactionDmNetTranID
                DisplayString,
        tuxDmTransactionDmBranchState
                INTEGER
        }



tuxDmTransactionDmlAccessPoint OBJECT-TYPE
        SYNTAX DisplayString (SIZE(1..30))
        ACCESS read-only
        STATUS mandatory
        DESCRIPTION
     "Name of the local domain access point with which the transaction is
     associated. This is a required field for GET operations. For SET
     operations, this variable must be specified."
        ::= { tuxDmTransactionEntry 10 }
 
tuxDmTransactionDmTpTranID OBJECT-TYPE
        SYNTAX DisplayString (SIZE(1..24))
        ACCESS read-write
        STATUS mandatory
        DESCRIPTION
     "Transaction identifier returned from tpsuspend(3c) mapped to a string
     representation. The data in this field should not be interpreted
     directly by the user except for equality comparison. For SET
     operations, this variable must be specified."
        ::= { tuxDmTransactionEntry 20 }
 
tuxDmTransactionState OBJECT-TYPE
        SYNTAX INTEGER {
                aborted(1),
                abortonly(2),
                active(3),
                comcalled(4),
                decided(5),
                done(6),
                habort(7),
                hcommit(8),
                heuristic(9),
                ready(10),
                unknown(11),
                invalid(12)
        }
        ACCESS read-write
        STATUS mandatory
        DESCRIPTION
     " This object denotes the current state of the tuxDmTransaction instance.
     GET requests: 
           aborted:    The transaction is being rolled back.
           abortonly:  The transaction has been identified for rollback.
           active:     The transaction is active.
           comcalled:  The transaction has initiated the first phase of
                       commitment.
           decided:    The transaction has initiated the second phase of
                       commitment.
           done:       The transaction has completed the second phase of
                       commitment.
           habort:     The transaction has been heuristically rolled back.
           hcommit:    The transaction has been heuristically committed.
           heuristic:  The transaction commitment or rollback has completed
                       heuristically. The branch state may give further
                       detail on which branch has completed heuristically.
           ready:      The transaction has completed the first phase of a
                       two phase commit. All the participating groups and
                       remote domains have completed the first phase of
                       commitment and are ready to be committed.
           unknown:    It was not possible to determine the state of the
                       transaction.

     SET requests: 

           invalid:  Forget the specified table entry. This
                     state change is only valid in states HCOmmit and
                     HABort."
        ::= { tuxDmTransactionEntry 30 }

tuxDmTransactionDmTxAccessPoint OBJECT-TYPE
        SYNTAX DisplayString (SIZE(1..30))
        ACCESS read-only
        STATUS mandatory
        DESCRIPTION
     "If the transaction originated from a remote domain, this
     is the name of the remote domain access point through which it
     originated. If the transaction originated within this domain,
     It is the name of the local domain access point."
        ::= { tuxDmTransactionEntry 40 }
 

tuxDmTransactionDmTxNetTranID OBJECT-TYPE
        SYNTAX DisplayString (SIZE(1..78))
        ACCESS read-only
        STATUS mandatory
        DESCRIPTION
     "If the transaction originated from a remote domain, It is
     the external transaction identifier received from the remote domain
     access point through which it originated. If the transaction originated
     within this domain, it contains the same value as the"
        ::= { tuxDmTransactionEntry 50 }

tuxDmTransactionDmBranchCount OBJECT-TYPE
        SYNTAX INTEGER
        ACCESS read-only
        STATUS mandatory
        DESCRIPTION
     "The number of branches to remote domain access points involved in the
     transaction. For a domain gateway that does not make branch information
     available, this value is zero."
        ::= { tuxDmTransactionEntry 60 }

tuxDmTransactionDmBranchIndex OBJECT-TYPE
        SYNTAX INTEGER
        ACCESS read-only
        STATUS mandatory
        DESCRIPTION
     "The index of the first branch-specific attribute values (tuxDmTransactionDmBranchNo,
     tuxDmTransactionDmrAccessPoint, tuxDmTransactionDmNetTranID, and tuxDmTransactionDmBranchState) corresponding
     to this object."
        ::= { tuxDmTransactionEntry 70 }

tuxDmTransactionDmBranchNo OBJECT-TYPE
        SYNTAX INTEGER
        ACCESS read-only
        STATUS mandatory
        DESCRIPTION
     "The branch number of the participating branch (numbered from zero)."
        ::= { tuxDmTransactionEntry 80 }

tuxDmTransactionDmrAccessPoint OBJECT-TYPE
        SYNTAX DisplayString (SIZE(1..30))
        ACCESS read-only
        STATUS mandatory
        DESCRIPTION
     "The name of the remote domain access point for this branch."
        ::= { tuxDmTransactionEntry 90 }

tuxDmTransactionDmNetTranID OBJECT-TYPE
        SYNTAX DisplayString (SIZE(1..78))
        ACCESS read-only
        STATUS mandatory
        DESCRIPTION
     "The external transaction identifier used with the remote domain access
     point for this branch. Some types of domain gateways do not return this
     information; in this scenario this attribute is set to the empty
     string. For example, TDomains uses the local transaction identifier in
     tuxDmTransactionDmTpTranID for branches to remote domain access points and sets this
     value to the empty string."
        ::= { tuxDmTransactionEntry 100 }

tuxDmTransactionDmBranchState OBJECT-TYPE
        SYNTAX INTEGER {
                aborted(1),
                abortonly(2),
                active(3),
                comcalled(4),
                decided(5),
                done(6),
                habort(7),
                hcommit(8),
                heuristic-hazard(9),
                heuristic-mixed(10),
                ready(11),
                unknown(12)
        }
        ACCESS read-write
        STATUS mandatory
        DESCRIPTION
          "A GET operation will retrieve runtime information for the
          transaction branch (when it is available for a particular domain
          gateway type).

           ABorteD:           The transaction branch is being rolled back
           ABortonlY:         The transaction branch has been identified
                              for rollback.
           ACTive:            The transaction branch is active.
           COMcalled:         The transaction branch has initiated the
                              first phase of commitment.
           DECided:           The transaction branch has initiated the
                              second phase of commitment.
           DONe:              The transaction branch has completed the
                              second phase of commitment.
           HABort:            The transaction has been heuristically rolled
                              back.
           HCOmmit:           The transaction has been heuristically
                              committed.
           Heuristic HaZard:  Communications for the transaction branch
                              failed, and it has not been determined if
                              rollback completed successfully.
           Heuristic MIxed:   The commitment or rollback for the
                              transaction branch has completed and the
                              remote domain has reported that the state of
                              some of the resources used for the commitment
                              or rollback is not consistent with the
                              outcome of the transaction.
           REAdy:             The transaction has completed the first phase
                              of a two-phase commit. All the participating
                              groups and remote domains have completed the
                              first phase of commitment and are ready to be
                              committed.
           UNKnown:           The state of the transaction could not be
                              determined."
        ::= { tuxDmTransactionEntry 110 }

-- Added : END-JANUS-NS-TUXEDO7.1-041400

-- **************************** END of TUXEDO MIB ********************
END
